module esc_port_forwarding {
  // Generated by yanger -t ncs
  tailf:ncs-device-type "netconf";

  namespace "http://www.cisco.com/esc/esc_port_forwarding";
  prefix esc_port_forwarding;

  import tailf-ncs {
    prefix ncs;
  }
  import tailf-common {
    prefix tailf;
  }

  organization "Cisco Systems";
  contact
    "Shesha Sreenivasamurthy <shesha@cisco.com>";
  description
    "ESC's port forwarding descriptions'";

  revision 2015-06-08 {
    description
      "added esc_port_forwarding";
  }

  grouping ncs_template_esc_port_forwarding {
    container port_forwarding {
      description
        "This section allows for specifying port(s) to be forwarded
         externally.";
      list port {
        // NCS patched for predictable order
        ordered-by user;
        key "type";
        leaf type {
          description
            "Type or purpose of the port to be forwarded";
          type string;
          // NCS drop mandatory statement
        }
        leaf protocol {
          description
            "Protocol type of traffic to be forwrded";
          type string;
          // NCS drop mandatory statement
        }
        leaf vnf_port {
          description
            "Internal port of VNF to be exposed externally.";
          type string;
          // NCS drop mandatory statement
        }
        list external_port_range {
          // NCS patched for predictable order
          ordered-by user;
          key "start end";
          description
            "Contiguous block of external ports can be specified using range.";
          leaf start {
            description
              "Starting external port in the range";
            type string;
          }
          leaf end {
            description
              "Ending external port in the range";
            type string;
          }
        }
      }
    }
  }

  grouping ncs_rpc_notif_esc_port_forwarding {
    container port_forwarding {
      description
        "This section allows for specifying port(s) to be forwarded
         externally.";
      list port {
        key "type";
        leaf type {
          description
            "Type or purpose of the port to be forwarded";
          type string;
          mandatory true;
        }
        leaf protocol {
          description
            "Protocol type of traffic to be forwrded";
          type string;
          mandatory true;
        }
        leaf vnf_port {
          description
            "Internal port of VNF to be exposed externally.";
          type uint16;
          mandatory true;
        }
        list external_port_range {
          key "start end";
          description
            "Contiguous block of external ports can be specified using range.";
          leaf start {
            description
              "Starting external port in the range";
            type uint16;
          }
          leaf end {
            description
              "Ending external port in the range";
            type uint16;
          }
        }
      }
    }
  }

  grouping live_ncs_esc_port_forwarding {
    container port_forwarding {
      description
        "This section allows for specifying port(s) to be forwarded
         externally.";
      list port {
        key "type";
        leaf type {
          description
            "Type or purpose of the port to be forwarded";
          type string;
          // NCS drop mandatory statement
        }
        leaf protocol {
          description
            "Protocol type of traffic to be forwrded";
          type string;
          // NCS drop mandatory statement
        }
        leaf vnf_port {
          description
            "Internal port of VNF to be exposed externally.";
          type uint16;
          // NCS drop mandatory statement
        }
        list external_port_range {
          key "start end";
          description
            "Contiguous block of external ports can be specified using range.";
          leaf start {
            description
              "Starting external port in the range";
            type uint16;
          }
          leaf end {
            description
              "Ending external port in the range";
            type uint16;
          }
        }
      }
    }
  }

  grouping esc_port_forwarding {
    container port_forwarding {
      description
        "This section allows for specifying port(s) to be forwarded
         externally.";
      list port {
        key "type";
        leaf type {
          description
            "Type or purpose of the port to be forwarded";
          type string;
          mandatory true;
        }
        leaf protocol {
          description
            "Protocol type of traffic to be forwrded";
          type string;
          mandatory true;
        }
        leaf vnf_port {
          description
            "Internal port of VNF to be exposed externally.";
          type uint16;
          mandatory true;
        }
        list external_port_range {
          key "start end";
          description
            "Contiguous block of external ports can be specified using range.";
          leaf start {
            description
              "Starting external port in the range";
            type uint16;
          }
          leaf end {
            description
              "Ending external port in the range";
            type uint16;
          }
        }
      }
    }
  }
}
