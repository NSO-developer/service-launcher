module esc_disk {

  namespace "http://www.cisco.com/esc/esc_disk";
  prefix "esc_disk";

  import ietf-inet-types { prefix "ietf-inet-types"; }
  import esc_types { prefix "types"; }
  import esc_locators { prefix "locators"; }

  organization "Cisco Systems";

  contact "Shesha Sreenivasamurthy <shesha@cisco.com>";

  description
    "ESC's disk descriptions'";


  revision 2016-07-14 {
    description "Added visibility string field to images";  
  }
  
  revision 2016-03-16 {
    description "Added extensible locator to images";  
  }
  revision 2015-08-18 {
    description "Remove image attribute 'public'";
  }
  revision 2015-06-29 {
    description "Datamodel change to support list of images";
  }
  revision 2015-06-04 {
    description "updated description";
  }
  revision 2014-06-23 {
    description "ESC Disk";
  }

  /*******************************************************************************/

  grouping disk_attributes {
    description "Disk properties are described in this section";
    leaf src {
      description
        "URL of the VM image from where it can be downloaded by ESC";
      type ietf-inet-types:uri;
      mandatory true;
    }
    leaf size {
      description
        "Size of the image specified by URL above. If unsure, leave it blank";
      type int32;
    }

    leaf sizeunit {
      description "Size unit. MiB/GiB/TiB/PiB/EiB";
      type types:szunits;
    }
    leaf disk_format {
      description "Format of the disk: qcow2, raw, vmdk";
      type types:disk_formats;
    }
    leaf container_format {
      description "";
      type string;
    }
    leaf serial_console {
      description "";
      type boolean;
    }
    leaf e1000_net {
      description "True if image has e1000 drivers";
      type boolean;
      default false;
    }
    leaf virtio_net {
      description "True if image has VIRTIO drivers";
      type boolean;
      default true;
    }
    leaf disk_bus {
      description "Root disk bus: ide, scsi, virtio";
      type types:iobus;
    }
    
    leaf visibility {
      description
        "Specifies whether image should be created as public or private";
      type string;
      default "public";
    }
    
    container properties {
      list property {
        key "name";
          description
            "Storage location for additional Image properties.";
          leaf name {
            description
              "Property key, for example maximum VCPUs supported by this VNF image.";
            type string;
            mandatory true;
          }  
          leaf type {
            description
              "Type of property.";
            type string;
          } 
          leaf-list value {
            description "One or more values";
            type string;
          }
      }
    }
  }
  grouping esc_disk {
    container disk {
      uses disk_attributes;
    }
  }
  grouping esc_images {
    container images {
      list image {
        description "List of images";
        key "name";
        leaf name {
          description "Name of the image";
          type types:escname;
          mandatory true;
        }
        uses disk_attributes;
        uses locators:extensible_locators;
      }
    }
  }
}
