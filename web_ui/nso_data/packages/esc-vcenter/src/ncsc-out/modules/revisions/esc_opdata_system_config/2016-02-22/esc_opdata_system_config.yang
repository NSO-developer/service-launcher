module esc_opdata_system_config {
  // Generated by yanger -t ncs
  tailf:ncs-device-type "netconf";

  namespace "http://www.cisco.com/esc/esc_opdata_system_config";
  prefix esc_opdata_system_config;

  import tailf-ncs {
    prefix ncs;
  }
  import tailf-common {
    prefix tailf;
  }

  organization "Cisco Systems";

  revision 2016-02-22 {
    description
      "Adding container for vmware vim config";
  }
  revision 2016-02-01 {
    description
      "ESC System Configuration details for operational data view";
  }

  grouping ncs_template_esc_opdata_system_config {
    description
      "This contains config data of this ESC VM ";
    container system_config {
      leaf active_vim {
        description
          "VIM type";
        type string;
      }
      container openstack_config {
        leaf os_auth_url {
          description
            "  The Openstack Authentication URL ";
          type string;
        }
        leaf admin_role {
          description
            " The Admin role setting ";
          type string;
        }
        leaf os_tenant_name {
          description
            " The Tenant name ";
          type string;
        }
        leaf os_username {
          description
            " The Openstack username ";
          type string;
        }
        leaf member_role {
          description
            " The Member role setting ";
          type string;
        }
      }
      container vmware_config {
        leaf vcenter_ip {
          description
            " The vcenter IP address ";
          type string;
        }
        leaf vcenter_port {
          description
            " The port number for vcenter connection ";
          type string;
        }
        leaf vcenter_username {
          description
            " The vcenter user name ";
          type string;
        }
      }
    }
  }

  grouping ncs_rpc_notif_esc_opdata_system_config {
    description
      "This contains config data of this ESC VM ";
    container system_config {
      leaf active_vim {
        description
          "VIM type";
        type string;
      }
      container openstack_config {
        leaf os_auth_url {
          description
            "  The Openstack Authentication URL ";
          type string;
        }
        leaf admin_role {
          description
            " The Admin role setting ";
          type string;
        }
        leaf os_tenant_name {
          description
            " The Tenant name ";
          type string;
        }
        leaf os_username {
          description
            " The Openstack username ";
          type string;
        }
        leaf member_role {
          description
            " The Member role setting ";
          type string;
        }
      }
      container vmware_config {
        leaf vcenter_ip {
          description
            " The vcenter IP address ";
          type string;
        }
        leaf vcenter_port {
          description
            " The port number for vcenter connection ";
          type string;
        }
        leaf vcenter_username {
          description
            " The vcenter user name ";
          type string;
        }
      }
    }
  }

  grouping live_ncs_esc_opdata_system_config {
    description
      "This contains config data of this ESC VM ";
    container system_config {
      leaf active_vim {
        description
          "VIM type";
        type string;
      }
      container openstack_config {
        leaf os_auth_url {
          description
            "  The Openstack Authentication URL ";
          type string;
        }
        leaf admin_role {
          description
            " The Admin role setting ";
          type string;
        }
        leaf os_tenant_name {
          description
            " The Tenant name ";
          type string;
        }
        leaf os_username {
          description
            " The Openstack username ";
          type string;
        }
        leaf member_role {
          description
            " The Member role setting ";
          type string;
        }
      }
      container vmware_config {
        leaf vcenter_ip {
          description
            " The vcenter IP address ";
          type string;
        }
        leaf vcenter_port {
          description
            " The port number for vcenter connection ";
          type string;
        }
        leaf vcenter_username {
          description
            " The vcenter user name ";
          type string;
        }
      }
    }
  }

  grouping esc_opdata_system_config {
    description
      "This contains config data of this ESC VM ";
    container system_config {
      leaf active_vim {
        description
          "VIM type";
        type string;
      }
      container openstack_config {
        leaf os_auth_url {
          description
            "  The Openstack Authentication URL ";
          type string;
        }
        leaf admin_role {
          description
            " The Admin role setting ";
          type string;
        }
        leaf os_tenant_name {
          description
            " The Tenant name ";
          type string;
        }
        leaf os_username {
          description
            " The Openstack username ";
          type string;
        }
        leaf member_role {
          description
            " The Member role setting ";
          type string;
        }
      }
      container vmware_config {
        leaf vcenter_ip {
          description
            " The vcenter IP address ";
          type string;
        }
        leaf vcenter_port {
          description
            " The port number for vcenter connection ";
          type string;
        }
        leaf vcenter_username {
          description
            " The vcenter user name ";
          type string;
        }
      }
    }
  }
}
