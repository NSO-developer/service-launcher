module esc_opdata_flavors {

  /*
   * This represents operational data of the flavors
   */

  namespace "http://www.cisco.com/esc/esc_opdata_flavors";

  prefix "esc_opdata_flavors";

  import ietf-yang-types { prefix "ietf-yang-types"; }
  import esc_opdata_flavor_state_machine { prefix "opstatemachines"; }

  organization "Cisco Systems";

  contact "Natasha Shrestha <nashrest@cisco.com>";

  revision 2015-07-06 {
    description
      "Elastic Services Controller Module's flavors' operational data";
  }

  grouping esc_opdata_flavors {
    description
      "This contains all the operational data of the flavors";
    container flavors {
      list flavor {
        description "Flavor running information";
        key "name";
        leaf name {
          description "Name of the flavor";
          type string;
        }
        leaf flavor_id {
          description "ID of the flavor";
          type ietf-yang-types:uuid;
        }
        leaf public {
          description "True if the flavor is public";
          type boolean;
          default true;
        }
        /* State Machine for Flavor */
        uses opstatemachines:esc_opdata_flavor_state_machine;
      }
    }
  }
}
