submodule esc_notifications {
  // Generated by yanger -t ncs
  belongs-to esc {
    prefix notifications;
  }

  import ietf-yang-types {
    prefix ietf-yang-types;
  }
  import esc_types {
    prefix types;
  }
  import esc_opdata_interface {
    prefix interface;
  }
  import esc_opdata_volumes {
    prefix volumes;
  }
  import esc_property {
    prefix property;
  }
  import tailf-ncs {
    prefix ncs;
  }
  import tailf-common {
    prefix tailf;
  }

  organization "Cisco Systems";
  contact
    "Shesha Sreenivasamurthy <shesha@cisco.com>";

  revision 2016-10-06 {
    description
      "Adding vim_connector_id and vim_user_id leaf to notifs";
  }
  revision 2016-08-04 {
    description
      "Adding properties in vminfo";
  }
  revision 2016-01-20 {
    description
      "Adding tenant UUID leaf to notifs";
  }
  revision 2015-07-16 {
    description
      "Notifications adding interface details for VM , Recovery and Scaling related events";
  }
  revision 2015-07-14 {
    description
      "Notifications adding interface details for VM , Recovery and Scaling related events";
  }
  revision 2015-06-29 {
    description
      "Notifications for image and flavor creation not associated
       with service";
  }
  revision 2015-06-10 {
    description
      "added hostname to vminfo";
  }
  revision 2014-10-03 {
    description
      "Notifications genenrated by ESC for consumption by its north
       bound clients";
  }

  grouping ncs_template_vminfo {
    leaf vmid {
      description
        "ID of the VM that is used internally by ESC";
      type string;
    }
    leaf hostid {
      description
        "ID of the HOST where VM is running that is used
         internally by ESC";
      type string;
    }
    leaf hostname {
      description
        "Name of the HOST where VM is running that is used
         internally by ESC";
      type string;
    }
    leaf software_version {
      description
        "Software version of the VM";
      type string;
    }
    uses interface:ncs_template_esc_opdata_interface;
    uses volumes:ncs_template_esc_opdata_volumes;
    uses property:ncs_template_property_list_definition;
  }

  grouping ncs_rpc_notif_vminfo {
    leaf vmid {
      description
        "ID of the VM that is used internally by ESC";
      type ietf-yang-types:uuid;
    }
    leaf hostid {
      description
        "ID of the HOST where VM is running that is used
         internally by ESC";
      type string;
    }
    leaf hostname {
      description
        "Name of the HOST where VM is running that is used
         internally by ESC";
      type string;
    }
    leaf software_version {
      description
        "Software version of the VM";
      type types:escname;
    }
    uses interface:ncs_rpc_notif_esc_opdata_interface;
    uses volumes:ncs_rpc_notif_esc_opdata_volumes;
    uses property:ncs_rpc_notif_property_list_definition;
  }

  grouping live_ncs_vminfo {
    leaf vmid {
      description
        "ID of the VM that is used internally by ESC";
      type ietf-yang-types:uuid;
    }
    leaf hostid {
      description
        "ID of the HOST where VM is running that is used
         internally by ESC";
      type string;
    }
    leaf hostname {
      description
        "Name of the HOST where VM is running that is used
         internally by ESC";
      type string;
    }
    leaf software_version {
      description
        "Software version of the VM";
      type types:escname;
    }
    uses interface:live_ncs_esc_opdata_interface;
    uses volumes:live_ncs_esc_opdata_volumes;
    uses property:live_ncs_property_list_definition;
  }

  grouping vminfo {
    leaf vmid {
      description
        "ID of the VM that is used internally by ESC";
      type ietf-yang-types:uuid;
    }
    leaf hostid {
      description
        "ID of the HOST where VM is running that is used
         internally by ESC";
      type string;
    }
    leaf hostname {
      description
        "Name of the HOST where VM is running that is used
         internally by ESC";
      type string;
    }
    leaf software_version {
      description
        "Software version of the VM";
      type types:escname;
    }
    uses interface:esc_opdata_interface;
    uses volumes:esc_opdata_volumes;
    uses property:property_list_definition;
  }

  augment "/ncs:devices/ncs:device/ncs:netconf-notifications/ncs:received-notifications/ncs:notification/ncs:data" {
    container escEvent {
      presence "";
      config false;
      leaf status {
        description
          "The event that is being notified is success or a failure";
        type types:status;
        // NCS drop mandatory statement
      }
      leaf status_code {
        description
          "The status code of the event notification";
        type int16;
        default "0";
      }
      leaf status_message {
        description
          "Discription of the status code";
        type string;
        // NCS drop mandatory statement
      }
      leaf network {
        description
          "Network name that was created or deleted";
        type string;
      }
      leaf subnet {
        description
          "Subnet name that was created or deleted";
        type string;
      }
      leaf image {
        description
          "Image name that was created or deleted";
        type string;
      }
      leaf flavor {
        description
          "Flavor name that was created or deleted";
        type string;
      }
      leaf svcname {
        description
          "Name of the service to which this VM belongs to";
        type types:escname;
      }
      leaf svcversion {
        description
          "Version of the service to which this VM belongs to";
        type types:escversion;
      }
      leaf depname {
        description
          "Name of the deployment to which this VM belongs to";
        type types:escname;
      }
      leaf tenant {
        description
          "Tenant name that was created or deleted or Name of the
              tenant to which this VM belongs to";
        type types:escname;
      }
      leaf tenant_id {
        description
          "External tenant UUID of the tenant";
        type string;
      }
      leaf svcid {
        description
          "ID of the service that is used internally by ESC to
           track the service";
        type string {
          length "1..41";
        }
      }
      leaf depid {
        description
          "ID of the deployment that is used internally by ESC
           to track the deployment";
        type string {
          length "1..41";
        }
      }
      leaf vm_group {
        description
          "Group/Type of VM to which the VMs specified in
           vm_source and vm_target belong";
        type types:escname;
      }
      leaf vim_connector_id {
        description
          "Vim connector id that was created, deleted or updated";
        type types:escname;
      }
      leaf vim_user_id {
        description
          "vim user id that was created, deleted or updated";
        type string;
      }
      container vm_source {
        description
          "Information of the VM that was:
                          Deployed or
                          Undeployed or
                          Overloded or
                          Underloaded or
                          Undeployed because of any un-natural reasons";
        uses vminfo;
      }
      container vm_target {
        description
          "Information of the VM that was:
           Deployed when vm_source contains
           information of overloaded VM Undeployed, and will
           be same as vm_source when vm_source containertains
           information of underloaded VM Deployed when
           vm_source contains information of the VM that died
           for any un-natural reasons";
        uses vminfo;
      }
      container policy {
        leaf condition {
          description
            "The policy condition that triggered this notify event";
          type types:policy_condition_type;
        }
        leaf action {
          description
            "The policy action name of the notify event";
          type string;
        }
        uses property:property_list_definition;
      }
      container event {
        description
          "This lest us know what event is this notification notifying.
           Additionally, from this one can infer what information
           vm_source and vm_target are referring to.";
        leaf type {
          description
            "Type of the event. As defined in EDCS: 1312696";
          type types:event_types;
          // NCS drop mandatory statement
        }
        leaf name {
          description
            "Name of the event. This is user defined in the datamodel.
             /esc_datamode/services/service_definition/
              vm_group/kpi_data/kpi/event_name";
          type string;
        }
        leaf threshold {
          description
            "Threshold value that was compared against that caused this event
             to be generated";
          type string {
            length "1..64";
          }
        }
        leaf value {
          description
            "Actual value of the variable tracked for
             scale-out/scale-in";
          type string {
            length "1..64";
          }
        }
        leaf details {
          description
            "Human-readable description";
          type string {
            length "1..1024";
          }
        }
      }
    }
  }
}
