module esc_opdata_volumes {
  // Generated by yanger -t ncs
  tailf:ncs-device-type "netconf";

  namespace "http://www.cisco.com/esc/esc_opdata_volumes";
  prefix esc_opdata_volumes;

  import ietf-yang-types {
    prefix ietf-yang-types;
  }
  import esc_types {
    prefix types;
  }
  import tailf-ncs {
    prefix ncs;
  }
  import tailf-common {
    prefix tailf;
  }

  organization "Cisco Systems";

  revision 2016-11-30 {
    description
      "Added image and volid to Volume list.";
  }
  revision 2016-01-19 {
    description
      "Added boot_index to Volume list.";
  }

  grouping ncs_template_esc_opdata_volumes {
    description
      "This contains all the operational data of the volumes for each VM";
    container volumes {
      list volume {
        // NCS patched for predictable order
        ordered-by user;
        key "display_name";
        description
          "Volume running information";
        leaf display_name {
          description
            "Display name of the Volume";
          type string;
        }
        leaf volid {
          description
            "The order of the Volumes attached to a VM";
          type string;
        }
        leaf external_id {
          description
            "UUID of the volume in the VIM.";
          type string;
        }
        leaf bus {
          description
            "Block device bus to be used: ide, scsi, virtio";
          type string;
        }
        leaf type {
          description
            "Type of the volume attached.";
          type string;
        }
        leaf size {
          description
            "Size of the Volume with unit.";
          type string;
        }
        leaf boot_index {
          description
            "Specify the boot order for bootable volumes.";
          type string;
        }
        leaf image {
          description
            "Name or UUID of the source image";
          type string;
        }
      }
    }
  }

  grouping ncs_rpc_notif_esc_opdata_volumes {
    description
      "This contains all the operational data of the volumes for each VM";
    container volumes {
      list volume {
        key "display_name";
        description
          "Volume running information";
        leaf display_name {
          description
            "Display name of the Volume";
          type types:escname;
        }
        leaf volid {
          description
            "The order of the Volumes attached to a VM";
          type uint16;
        }
        leaf external_id {
          description
            "UUID of the volume in the VIM.";
          type ietf-yang-types:uuid;
        }
        leaf bus {
          description
            "Block device bus to be used: ide, scsi, virtio";
          type string;
        }
        leaf type {
          description
            "Type of the volume attached.";
          type types:escname;
        }
        leaf size {
          description
            "Size of the Volume with unit.";
          type string;
        }
        leaf boot_index {
          description
            "Specify the boot order for bootable volumes.";
          type string;
        }
        leaf image {
          description
            "Name or UUID of the source image";
          type string;
        }
      }
    }
  }

  grouping live_ncs_esc_opdata_volumes {
    description
      "This contains all the operational data of the volumes for each VM";
    container volumes {
      list volume {
        key "display_name";
        description
          "Volume running information";
        leaf display_name {
          description
            "Display name of the Volume";
          type types:escname;
        }
        leaf volid {
          description
            "The order of the Volumes attached to a VM";
          type uint16;
        }
        leaf external_id {
          description
            "UUID of the volume in the VIM.";
          type ietf-yang-types:uuid;
        }
        leaf bus {
          description
            "Block device bus to be used: ide, scsi, virtio";
          type string;
        }
        leaf type {
          description
            "Type of the volume attached.";
          type types:escname;
        }
        leaf size {
          description
            "Size of the Volume with unit.";
          type string;
        }
        leaf boot_index {
          description
            "Specify the boot order for bootable volumes.";
          type string;
        }
        leaf image {
          description
            "Name or UUID of the source image";
          type string;
        }
      }
    }
  }

  grouping esc_opdata_volumes {
    description
      "This contains all the operational data of the volumes for each VM";
    container volumes {
      list volume {
        key "display_name";
        description
          "Volume running information";
        leaf display_name {
          description
            "Display name of the Volume";
          type types:escname;
        }
        leaf volid {
          description
            "The order of the Volumes attached to a VM";
          type uint16;
        }
        leaf external_id {
          description
            "UUID of the volume in the VIM.";
          type ietf-yang-types:uuid;
        }
        leaf bus {
          description
            "Block device bus to be used: ide, scsi, virtio";
          type string;
        }
        leaf type {
          description
            "Type of the volume attached.";
          type types:escname;
        }
        leaf size {
          description
            "Size of the Volume with unit.";
          type string;
        }
        leaf boot_index {
          description
            "Specify the boot order for bootable volumes.";
          type string;
        }
        leaf image {
          description
            "Name or UUID of the source image";
          type string;
        }
      }
    }
  }
}
