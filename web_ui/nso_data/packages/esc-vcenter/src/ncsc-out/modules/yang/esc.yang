module esc {
  // Generated by yanger -t ncs
  tailf:ncs-device-type "netconf";

  namespace "http://www.cisco.com/esc/esc";
  prefix esc;

  import esc_datamodel {
    prefix dm;
  }
  import tailf-common {
    prefix tailf;
  }
  import esc_opdata {
    prefix op;
  }
  import esc_info {
    prefix info;
  }
  import esc_types {
    prefix types;
  }
  import esc_network {
    prefix network;
  }
  import esc_disk {
    prefix disk;
  }
  import esc_flavor {
    prefix flavor;
  }
  import esc_vim_connector {
    prefix vim;
  }
  include esc_notifications;
  import tailf-ncs {
    prefix ncs;
  }

  organization "Cisco Systems";
  contact
    "Shesha Sreenivasamurthy <shesha@cisco.com>";
  description
    "YANG version of the Elastic Service Controller.  This is a complete
     service orchestration module that can dynamically expand and
     reduce your service capacity based on your description of
     LOAD. This module guarantees that the services will be online
     until you tear it down.  This module enables your to: (config it)
     -> (deploy it) -> (forget it)";

  revision 2016-12-02 {
    description
      "Normalize new LCS policy names";
  }
  revision 2016-11-28 {
    description
      "Generic LCS_NOTIFY policy action support";
  }
  revision 2016-11-11 {
    description
      "VM-level software update LCS support";
  }
  revision 2016-11-08 {
    description
      "Add new api filterLog to query for logs in escmanager with given parameters.";
  }
  revision 2016-10-18 {
    description
      "Update placement_group description";
  }
  revision 2016-10-18 {
    description
      "Remove container default bandwidth values from esc_interface.yang";
  }
  revision 2016-10-06 {
    description
      "add vim connector and user id in notification";
  }
  revision 2016-10-05 {
    description
      "Add reboot_time(esc_datamodle.yang)";
  }
  revision 2016-10-04 {
    description
      "Add more LCS conditions (esc_types.yang)";
  }
  revision 2016-09-23 {
    description
      "Add top level container esc_system_config containing vim_connectors";
  }
  revision 2016-08-04 {
    description
      "add extra vm info in notification";
  }
  revision 2016-07-28 {
    description
      "Added prefix choice for subnet masks";
  }
  revision 2016-07-21 {
    description
      "Added template_engine field to config data configuration to support no token replacement";
  }
  revision 2016-03-01 {
    description
      "Added support for recovery VM operations";
  }
  revision 2015-07-23 {
    description
      "Added support for Tenant Network creation-network directly under tenant";
  }
  revision 2015-07-14 {
    description
      "Added a new deployment model under tenant";
  }
  revision 2015-06-29 {
    description
      "ESC Datamodel change to support independent creation of
       images and flavors";
  }
  revision 2014-06-23 {
    description
      "Elastic Services Controller Module";
  }

  augment "/ncs:devices/ncs:device/ncs:rpc" {
    container rpc-filterLog {
      tailf:ncs-device-type "netconf";
      tailf:display-when "not(../../ncs:module) or ../../ncs:module[ncs:name='esc']";
      tailf:action filterLog {
        tailf:actionpoint ncsproxy {
          tailf:internal;
        }
        description
          "Query and filter escmanager logs using given parameters";
        // NCS drop tailf:actionpoint
        input {
          leaf log_level {
            mandatory false;
            description
              "One of DEBUG / INFO / WARNING / ERROR / TRACE / FATAL. Results will include all logs at and
               above the level specified";
            type types:log_level_types;
            default "ERROR";
          }
          leaf log_count {
            mandatory false;
            description
              "Number of logs to return";
            type uint32;
            default "10";
          }
          container classifications {
            leaf-list classification {
              description
                "Classification values to be used for the log filtering.  For example: 'OS', 'SM'.
                 Logs containing any of the provided classification values will be returned.";
              type types:log_classification_types;
            }
          }
          container tags {
            list tag {
              key "name";
              leaf name {
                mandatory true;
                description
                  "Tag name to be used for the log filtering.  For example: 'tenant', 'depName'.
                   Logs containing any of the provided tag name plus the tag values will be returned.";
                type types:log_tag_types;
              }
              leaf value {
                mandatory true;
                description
                  "Tag value pairs to be used for the log filtering.  For example: 'adminTenant', 'CSRDeployment'";
                type string;
              }
            }
          }
        }
        output {
          container filterLogResults {
            leaf log_level {
              description
                "Log level used to filter for the logs.";
              type types:log_level_types;
            }
            list logs {
              container classifications {
                leaf-list classification {
                  description
                    "Classifications used to filter for the logs.";
                  type types:log_classification_types;
                }
              }
              container tags {
                list tag {
                  key "name";
                  leaf name {
                    mandatory true;
                    description
                      "Tag name used to filter for the logs.";
                    type types:log_tag_types;
                  }
                  leaf value {
                    mandatory true;
                    description
                      "Tag value used to filter for the logs.";
                    type string;
                  }
                }
              }
              leaf log_date_time {
                description
                  "Timestamp of the log.";
                type string;
              }
              leaf log_message {
                description
                  "The log message.";
                type string;
              }
            }
          }
        }
      }
    }
  }
  augment "/ncs:devices/ncs:device-group/ncs:rpc" {
    container rpc-filterLog {
      tailf:ncs-device-type "netconf";
      tailf:display-when "/ncs:devices/ncs:device[ncs:name=current()/../../ncs:member]/ncs:module[ncs:name='esc']";
      tailf:action filterLog {
        tailf:actionpoint ncsproxy {
          tailf:internal;
        }
        description
          "Query and filter escmanager logs using given parameters";
        // NCS drop tailf:actionpoint
        input {
          leaf log_level {
            mandatory false;
            description
              "One of DEBUG / INFO / WARNING / ERROR / TRACE / FATAL. Results will include all logs at and
               above the level specified";
            type types:log_level_types;
            default "ERROR";
          }
          leaf log_count {
            mandatory false;
            description
              "Number of logs to return";
            type uint32;
            default "10";
          }
          container classifications {
            leaf-list classification {
              description
                "Classification values to be used for the log filtering.  For example: 'OS', 'SM'.
                 Logs containing any of the provided classification values will be returned.";
              type types:log_classification_types;
            }
          }
          container tags {
            list tag {
              key "name";
              leaf name {
                mandatory true;
                description
                  "Tag name to be used for the log filtering.  For example: 'tenant', 'depName'.
                   Logs containing any of the provided tag name plus the tag values will be returned.";
                type types:log_tag_types;
              }
              leaf value {
                mandatory true;
                description
                  "Tag value pairs to be used for the log filtering.  For example: 'adminTenant', 'CSRDeployment'";
                type string;
              }
            }
          }
        }
        output {
          container "device" {
            leaf "name" {
              type string;
            }
            leaf "info" {
              type string;
            }
            container "result" {
              container filterLogResults {
                leaf log_level {
                  description
                    "Log level used to filter for the logs.";
                  type types:log_level_types;
                }
                list logs {
                  container classifications {
                    leaf-list classification {
                      description
                        "Classifications used to filter for the logs.";
                      type types:log_classification_types;
                    }
                  }
                  container tags {
                    list tag {
                      key "name";
                      leaf name {
                        mandatory true;
                        description
                          "Tag name used to filter for the logs.";
                        type types:log_tag_types;
                      }
                      leaf value {
                        mandatory true;
                        description
                          "Tag value used to filter for the logs.";
                        type string;
                      }
                    }
                  }
                  leaf log_date_time {
                    description
                      "Timestamp of the log.";
                    type string;
                  }
                  leaf log_message {
                    description
                      "The log message.";
                    type string;
                  }
                }
              }
            }
          }
        }
      }
    }
  }
  augment "/ncs:devices/ncs:device/ncs:rpc" {
    container rpc-hostAction {
      tailf:ncs-device-type "netconf";
      tailf:display-when "not(../../ncs:module) or ../../ncs:module[ncs:name='esc']";
      tailf:action hostAction {
        tailf:actionpoint ncsproxy {
          tailf:internal;
        }
        description
          "Host actions including enable and disable";
        // NCS drop tailf:actionpoint
        input {
          leaf actionType {
            mandatory true;
            description
              "VM action type";
            type types:host_action_type;
          }
          leaf hostName {
            mandatory true;
            description
              "Host Name";
            type types:escname;
          }
        }
      }
    }
  }
  augment "/ncs:devices/ncs:device-group/ncs:rpc" {
    container rpc-hostAction {
      tailf:ncs-device-type "netconf";
      tailf:display-when "/ncs:devices/ncs:device[ncs:name=current()/../../ncs:member]/ncs:module[ncs:name='esc']";
      tailf:action hostAction {
        tailf:actionpoint ncsproxy {
          tailf:internal;
        }
        description
          "Host actions including enable and disable";
        // NCS drop tailf:actionpoint
        input {
          leaf actionType {
            mandatory true;
            description
              "VM action type";
            type types:host_action_type;
          }
          leaf hostName {
            mandatory true;
            description
              "Host Name";
            type types:escname;
          }
        }
      }
    }
  }
  augment "/ncs:devices/ncs:device/ncs:rpc" {
    container rpc-recoveryVmAction {
      tailf:ncs-device-type "netconf";
      tailf:display-when "not(../../ncs:module) or ../../ncs:module[ncs:name='esc']";
      tailf:action recoveryVmAction {
        tailf:actionpoint ncsproxy {
          tailf:internal;
        }
        description
          "Recovery VM actions including do and donot.";
        // NCS drop tailf:actionpoint
        input {
          leaf actionType {
            mandatory true;
            description
              "Recovery VM action type";
            type types:recovery_op_types;
          }
          leaf vmName {
            mandatory true;
            description
              "VM Name";
            type types:escname;
          }
        }
      }
    }
  }
  augment "/ncs:devices/ncs:device-group/ncs:rpc" {
    container rpc-recoveryVmAction {
      tailf:ncs-device-type "netconf";
      tailf:display-when "/ncs:devices/ncs:device[ncs:name=current()/../../ncs:member]/ncs:module[ncs:name='esc']";
      tailf:action recoveryVmAction {
        tailf:actionpoint ncsproxy {
          tailf:internal;
        }
        description
          "Recovery VM actions including do and donot.";
        // NCS drop tailf:actionpoint
        input {
          leaf actionType {
            mandatory true;
            description
              "Recovery VM action type";
            type types:recovery_op_types;
          }
          leaf vmName {
            mandatory true;
            description
              "VM Name";
            type types:escname;
          }
        }
      }
    }
  }
  augment "/ncs:devices/ncs:device/ncs:rpc" {
    container rpc-vmAction {
      tailf:ncs-device-type "netconf";
      tailf:display-when "not(../../ncs:module) or ../../ncs:module[ncs:name='esc']";
      tailf:action vmAction {
        tailf:actionpoint ncsproxy {
          tailf:internal;
        }
        description
          "VM actions including stop, start, reboot, disable-monitor and enable monitor.";
        // NCS drop tailf:actionpoint
        input {
          leaf actionType {
            mandatory true;
            description
              "VM action type";
            type types:action_types;
          }
          leaf vmName {
            mandatory true;
            description
              "VM Name";
            type types:escname;
          }
        }
      }
    }
  }
  augment "/ncs:devices/ncs:device-group/ncs:rpc" {
    container rpc-vmAction {
      tailf:ncs-device-type "netconf";
      tailf:display-when "/ncs:devices/ncs:device[ncs:name=current()/../../ncs:member]/ncs:module[ncs:name='esc']";
      tailf:action vmAction {
        tailf:actionpoint ncsproxy {
          tailf:internal;
        }
        description
          "VM actions including stop, start, reboot, disable-monitor and enable monitor.";
        // NCS drop tailf:actionpoint
        input {
          leaf actionType {
            mandatory true;
            description
              "VM action type";
            type types:action_types;
          }
          leaf vmName {
            mandatory true;
            description
              "VM Name";
            type types:escname;
          }
        }
      }
    }
  }
  augment "/ncs:devices/ncs:device/ncs:rpc" {
    container rpc-serviceAction {
      tailf:ncs-device-type "netconf";
      tailf:display-when "not(../../ncs:module) or ../../ncs:module[ncs:name='esc']";
      tailf:action serviceAction {
        tailf:actionpoint ncsproxy {
          tailf:internal;
        }
        description
          "Service actions including stop, start, reboot, disable-monitor and enable monitor.";
        // NCS drop tailf:actionpoint
        input {
          leaf actionType {
            mandatory true;
            description
              "Service action type";
            type types:action_types;
          }
          leaf tenantName {
            mandatory true;
            description
              "Tenant Name";
            type types:escname;
          }
          leaf depName {
            mandatory true;
            description
              "Deployment Name";
            type types:escname;
          }
          leaf serviceName {
            mandatory true;
            description
              "Service Name";
            type types:escname;
          }
          leaf serviceVersion {
            mandatory true;
            description
              "Service Version";
            type types:escname;
          }
        }
      }
    }
  }
  augment "/ncs:devices/ncs:device-group/ncs:rpc" {
    container rpc-serviceAction {
      tailf:ncs-device-type "netconf";
      tailf:display-when "/ncs:devices/ncs:device[ncs:name=current()/../../ncs:member]/ncs:module[ncs:name='esc']";
      tailf:action serviceAction {
        tailf:actionpoint ncsproxy {
          tailf:internal;
        }
        description
          "Service actions including stop, start, reboot, disable-monitor and enable monitor.";
        // NCS drop tailf:actionpoint
        input {
          leaf actionType {
            mandatory true;
            description
              "Service action type";
            type types:action_types;
          }
          leaf tenantName {
            mandatory true;
            description
              "Tenant Name";
            type types:escname;
          }
          leaf depName {
            mandatory true;
            description
              "Deployment Name";
            type types:escname;
          }
          leaf serviceName {
            mandatory true;
            description
              "Service Name";
            type types:escname;
          }
          leaf serviceVersion {
            mandatory true;
            description
              "Service Version";
            type types:escname;
          }
        }
      }
    }
  }
  augment "/ncs:devices/ncs:device/ncs:config" {
    container esc_datamodel {
      presence "In NCS this node is optional";
      tailf:ncs-device-type "netconf";
      tailf:display-when "not(../../ncs:module) or ../../ncs:module[ncs:name='esc']";
      description
        "Top-level container for all ESC database objects.";
      // NCS drop config false leaf version
      uses dm:svc_datamodel;
      container tenants {
        list tenant {
          key "name";
          description
            "List of tenants";
          leaf name {
            type types:escname;
            mandatory true;
          }
          leaf managed_resource {
            type boolean;
            default "true";
          }
          uses network:esc_network;
          uses dm:tenant_datamodel;
          uses dm:tenant_dep_model;
        }
      }
      uses network:esc_network;
      uses disk:esc_images;
      uses flavor:esc_flavors;
      // NCS drop config false container opdata
      // NCS drop config false container info
    }
    container esc_system_config {
      tailf:ncs-device-type "netconf";
      tailf:display-when "not(../../ncs:module) or ../../ncs:module[ncs:name='esc']";
      description
        "Top-level container for all ESC system configs.";
      uses vim:esc_vim_connector;
    }
  }
  augment "/ncs:devices/ncs:device/ncs:live-status" {
    container esc_datamodel {
      presence "In NCS this node is optional";
      tailf:ncs-device-type "netconf";
      tailf:display-when "not(../../ncs:module) or ../../ncs:module[ncs:name='esc'] or (../../ncs:live-status-protocol[not(ncs:capability)]) or (../../ncs:live-status-protocol/ncs:capability/ncs:module[.='esc'])";
      description
        "Top-level container for all ESC database objects.";
      leaf version {
        type types:escversion;
        // NCS drop mandatory statement
        description
          "ESC version";
      }
      uses dm:live_ncs_svc_datamodel;
      container tenants {
        list tenant {
          key "name";
          description
            "List of tenants";
          leaf name {
            type types:escname;
            // NCS drop mandatory statement
          }
          leaf managed_resource {
            type boolean;
            // NCS drop default statement
          }
          uses network:live_ncs_esc_network;
          uses dm:live_ncs_tenant_datamodel;
          uses dm:live_ncs_tenant_dep_model;
        }
      }
      uses network:live_ncs_esc_network;
      uses disk:live_ncs_esc_images;
      uses flavor:live_ncs_esc_flavors;
      container opdata {
        presence "Indicates that ESC has exported some operational data";
        description
          "This contains all the operational data of the services that have been
           registered and/or instantiated. This is operational data,
           means it is READ-ONLY. Subtrees under this will inherit
           READ-ONLY property, thereby entire subtree becomes READ-ONLY";
        // NCS drop tailf:callpoint
        uses op:live_ncs_esc_opdata;
      }
      container info {
        presence "Indicates that ESC has exported its infomation";
        description
          "This contains all the information related to versions and copytights";
        // NCS drop tailf:callpoint
        uses info:live_ncs_esc_info;
      }
    }
    container esc_system_config {
      tailf:ncs-device-type "netconf";
      tailf:display-when "not(../../ncs:module) or ../../ncs:module[ncs:name='esc'] or (../../ncs:live-status-protocol[not(ncs:capability)]) or (../../ncs:live-status-protocol/ncs:capability/ncs:module[.='esc'])";
      description
        "Top-level container for all ESC system configs.";
      uses vim:live_ncs_esc_vim_connector;
    }
  }
  augment "/ncs:devices/ncs:template/ncs:config" {
    container esc_datamodel {
      presence "In NCS this node is optional";
      description
        "Top-level container for all ESC database objects.";
      // NCS drop config false leaf version
      uses dm:ncs_template_svc_datamodel;
      container tenants {
        list tenant {
          // NCS patched for predictable order
          ordered-by user;
          key "name";
          description
            "List of tenants";
          leaf name {
            type string;
            // NCS drop mandatory statement
          }
          leaf managed_resource {
            type string;
            // NCS drop default statement
          }
          uses network:ncs_template_esc_network;
          uses dm:ncs_template_tenant_datamodel;
          uses dm:ncs_template_tenant_dep_model;
        }
      }
      uses network:ncs_template_esc_network;
      uses disk:ncs_template_esc_images;
      uses flavor:ncs_template_esc_flavors;
      // NCS drop config false container opdata
      // NCS drop config false container info
    }
    container esc_system_config {
      description
        "Top-level container for all ESC system configs.";
      uses vim:ncs_template_esc_vim_connector;
    }
  }
}
