module esc_opdata_interface {

  /*
   * This represents operational data of the interfaces of the VM
   */

  namespace "http://www.cisco.com/esc/esc_opdata_interface";

  prefix "esc_opdata_interface";

  import esc_types { prefix "types"; }

  organization "Cisco Systems";

  contact "Shesha Sreenivasamurthy <shesha@cisco.com>";
  
  revision 2016-04-27 {
    description "Adding type to the interface";
  }
  revision 2016-01-25 {
    description "Adding model to the interface";
  }
  
  revision 2015-11-09 {
    description "Added security groups leaf for the interface";
  }
  revision 2015-08-31 {
    description "Altering id types for port, network and subnet to be strings rather than UUIDs";
  }
  revision 2015-07-02 {
    description "Added netmask and gateway to the interface";
  }
  revision 2015-06-18 {
    description "Added port_forwards";
  }
  revision 2014-12-03 {
    description "Added NIC ID to the interface and changed the key";
  }
  revision 2014-08-06 {
    description "Elastic Services Controller Module's tenant's interface's
                operational data";
  }

  grouping esc_opdata_interface {
    description
      "This contains all the operational data of the interface for each VM";
    container interfaces {
      list interface {
        key "nicid";
        description "Interface running information";
        leaf nicid {
          description "ID of the interface specified during configuration";
          type uint16;
        }
        leaf model {
          description
            "In case of virtual: e1000, virtio etc. In case of passthrough:
             Model of the NIC. This will be specific to the data center. Data
             centers may have NICs that support virtual functions from
             different vendors, like Intel, Cisco etc.";
          type types:iface_model;
        }
        leaf type {
          description "Interface Type: virtual/passthru";
          type string;
        }
        leaf port_id {
          description "Port identifier";
          type string;
        }
        leaf network {
          description "Network to which this interface is attached";
          type string;
        }
        leaf subnet {
          description "Sub Network to which this interface is attached";
          type string;
        }
        leaf ip_address {
          description "IP address for this interface";
          type types:escipaddr;
        }
        leaf mac_address {
          description "MAC address for this interface";
          type types:escmacaddr;
        }
        leaf netmask {
          description "Netmask of the subnet";
          type types:escipaddr;
        }
        leaf gateway {
          description "Gateway of the subnet";
          type types:escipaddr; 
        }
        leaf security_groups {
          description "List of delimiter-separated security groups for the interface";
          type string;
        }
        container port_forwards {
          description "This section contains teh forwarded prts on this interface";
          list port_forward {
            key "port_type";
            leaf port_type {
              description "Purpose of the forwarded port. For example ssh, telnet, etc.";
              type string;
            }
            leaf port_number {
              description "The external port number for this interface";
              type uint16;
            }
          }
        }
      }
    }
  }
}
