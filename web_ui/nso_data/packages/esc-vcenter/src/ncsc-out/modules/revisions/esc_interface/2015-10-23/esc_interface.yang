module esc_interface {
  // Generated by yanger -t ncs
  tailf:ncs-device-type "netconf";

  namespace "http://www.cisco.com/esc/esc_interface";
  prefix esc_interface;

  import esc_types {
    prefix types;
  }
  import esc_port_forwarding {
    prefix port_forwarding;
  }
  import tailf-ncs {
    prefix ncs;
  }
  import tailf-common {
    prefix tailf;
  }

  organization "Cisco Systems";
  contact
    "Shesha Sreenivasamurthy <shesha@cisco.com>";
  description
    "ESC's interface descriptions'";

  revision 2015-10-23 {
    description
      "Add security_groups container for security_group leaf-list within interface";
  }
  revision 2015-10-22 {
    description
      "Add security_group leaf within interface";
  }
  revision 2015-08-21 {
    description
      "Add subnet leaf within interface";
  }
  revision 2015-07-20 {
    description
      "In interface list removed the must condition on nicid";
  }
  revision 2015-06-09 {
    description
      "added allowed_address_pair support for ip and network list";
  }
  revision 2015-06-08 {
    description
      "added esc_port_forwarding";
  }
  revision 2015-06-04 {
    description
      "updated description";
  }
  revision 2014-06-23 {
    description
      "ESC Interface";
  }

  grouping ncs_template_esc_interface {
    container interfaces {
      description
        "Specification of number of interfaces and properties for each
         interface. The order of the interfaces specified here does
         not correspond to the order of the interfaces in the VM.";
      list interface {
        // NCS patched for predictable order
        ordered-by user;
        key "nicid";
        leaf nicid {
          description
            "ID for the interfaces. This determines the order
             in which interfaces are presented to the guest VM";
          type string;
          // NCS drop mandatory statement
        }
        leaf type {
          description
            "Interface Type: virtual/passthru";
          type string;
          // NCS drop default statement
        }
        leaf model {
          description
            "In case of vitrual: e1000 or virtio. In case of passthrough:
             Model of the NIC. This will be specific to the data center. Data
             centers may have NICs that support virtual functions from
             different vendors, like Intel, Cisco etc. Passthrough is
             not currently supported therefore, not exposing the
             models relavent to PASSTHROUGH as identities";
          type string;
          // NCS drop default statement
        }
        leaf network {
          description
            "Network to which this interface needs to be attached.";
          type string;
          // NCS drop mandatory statement
        }
        leaf subnet {
          description
            "Subnet within the network to where the port needs to be created.";
          type string;
        }
        leaf anycast_address {
          description
            "Anycast address corresponding to this interface";
          type string;
        }
        leaf ip_address {
          description
            "Static IP address for this interface";
          type string;
        }
        leaf mac_address {
          description
            "Static MAC address for this interface";
          type string;
        }
        container bandwidth {
          leaf min {
            description
              "Minimum bandwidth required for this interface in Mbps";
            type string;
          }
          leaf max {
            description
              "Maximum bandwidth required for this interface in Mbps";
            type string;
          }
        }
        container security_groups {
          description
            "Containter for security group(s) set for this instance";
          leaf-list security_group {
            // NCS patched for predictable order
            ordered-by user;
            description
              "IP filter rules that determine access control for the VM instance";
            type string;
          }
        }
        container allowed_address_pairs {
          description
            "The allowed address is allows one to specify
             arbitrary mac_address/ip_address(cidr) pairs that are
             allowed to pass through a port regardless of subnet.";
          list network {
            // NCS patched for predictable order
            ordered-by user;
            key "name";
            description
              "Network allowed on this interface";
            leaf name {
              description
                "Network name or uuid";
              type string;
              // NCS drop mandatory statement
            }
          }
          list address {
            // NCS patched for predictable order
            ordered-by user;
            key "ip_address";
            description
              "Allowed address on this interface";
            leaf ip_address {
              description
                "Ip address or Subnet address for this network.";
              type string;
              // NCS drop mandatory statement
            }
            leaf netmask {
              description
                "Netmask for the subnet";
              type string;
            }
          }
        }
        uses port_forwarding:ncs_template_esc_port_forwarding;
      }
    }
  }

  grouping ncs_rpc_notif_esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          mandatory true;
        }
        leaf type {
          description
            "Interface Type: virtual/passthru";
          type types:iface_type;
          default "virtual";
        }
        leaf model {
          description
            "In case of vitrual: e1000 or virtio. In case of passthrough:
             Model of the NIC. This will be specific to the data center. Data
             centers may have NICs that support virtual functions from
             different vendors, like Intel, Cisco etc. Passthrough is
             not currently supported therefore, not exposing the
             models relavent to PASSTHROUGH as identities";
          type types:iface_model;
          default "virtio";
        }
        leaf network {
          description
            "Network to which this interface needs to be attached.";
          type types:escnetname;
          mandatory true;
        }
        leaf subnet {
          description
            "Subnet within the network to where the port needs to be created.";
          type types:escnetname;
        }
        leaf anycast_address {
          description
            "Anycast address corresponding to this interface";
          type types:escipaddr;
        }
        leaf ip_address {
          description
            "Static IP address for this interface";
          type types:escipaddr;
        }
        leaf mac_address {
          description
            "Static MAC address for this interface";
          type types:escmacaddr;
        }
        container bandwidth {
          leaf min {
            description
              "Minimum bandwidth required for this interface in Mbps";
            type int32;
          }
          leaf max {
            description
              "Maximum bandwidth required for this interface in Mbps";
            type int32;
          }
        }
        container security_groups {
          description
            "Containter for security group(s) set for this instance";
          leaf-list security_group {
            description
              "IP filter rules that determine access control for the VM instance";
            type types:escnetname;
          }
        }
        container allowed_address_pairs {
          description
            "The allowed address is allows one to specify
             arbitrary mac_address/ip_address(cidr) pairs that are
             allowed to pass through a port regardless of subnet.";
          list network {
            key "name";
            description
              "Network allowed on this interface";
            leaf name {
              description
                "Network name or uuid";
              type types:escnetname;
              mandatory true;
            }
          }
          list address {
            key "ip_address";
            description
              "Allowed address on this interface";
            leaf ip_address {
              description
                "Ip address or Subnet address for this network.";
              type types:escipaddr;
              mandatory true;
            }
            leaf netmask {
              description
                "Netmask for the subnet";
              type types:escipaddr;
            }
          }
        }
        uses port_forwarding:ncs_rpc_notif_esc_port_forwarding;
      }
    }
  }

  grouping live_ncs_esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          // NCS drop mandatory statement
        }
        leaf type {
          description
            "Interface Type: virtual/passthru";
          type types:iface_type;
          // NCS drop default statement
        }
        leaf model {
          description
            "In case of vitrual: e1000 or virtio. In case of passthrough:
             Model of the NIC. This will be specific to the data center. Data
             centers may have NICs that support virtual functions from
             different vendors, like Intel, Cisco etc. Passthrough is
             not currently supported therefore, not exposing the
             models relavent to PASSTHROUGH as identities";
          type types:iface_model;
          // NCS drop default statement
        }
        leaf network {
          description
            "Network to which this interface needs to be attached.";
          type types:escnetname;
          // NCS drop mandatory statement
        }
        leaf subnet {
          description
            "Subnet within the network to where the port needs to be created.";
          type types:escnetname;
        }
        leaf anycast_address {
          description
            "Anycast address corresponding to this interface";
          type types:escipaddr;
        }
        leaf ip_address {
          description
            "Static IP address for this interface";
          type types:escipaddr;
        }
        leaf mac_address {
          description
            "Static MAC address for this interface";
          type types:escmacaddr;
        }
        container bandwidth {
          leaf min {
            description
              "Minimum bandwidth required for this interface in Mbps";
            type int32;
          }
          leaf max {
            description
              "Maximum bandwidth required for this interface in Mbps";
            type int32;
          }
        }
        container security_groups {
          description
            "Containter for security group(s) set for this instance";
          leaf-list security_group {
            description
              "IP filter rules that determine access control for the VM instance";
            type types:escnetname;
          }
        }
        container allowed_address_pairs {
          description
            "The allowed address is allows one to specify
             arbitrary mac_address/ip_address(cidr) pairs that are
             allowed to pass through a port regardless of subnet.";
          list network {
            key "name";
            description
              "Network allowed on this interface";
            leaf name {
              description
                "Network name or uuid";
              type types:escnetname;
              // NCS drop mandatory statement
            }
          }
          list address {
            key "ip_address";
            description
              "Allowed address on this interface";
            leaf ip_address {
              description
                "Ip address or Subnet address for this network.";
              type types:escipaddr;
              // NCS drop mandatory statement
            }
            leaf netmask {
              description
                "Netmask for the subnet";
              type types:escipaddr;
            }
          }
        }
        uses port_forwarding:live_ncs_esc_port_forwarding;
      }
    }
  }

  grouping esc_interface {
    container interfaces {
      description
        "Specification of number of interfaces and properties for each
         interface. The order of the interfaces specified here does
         not correspond to the order of the interfaces in the VM.";
      list interface {
        key "nicid";
        leaf nicid {
          description
            "ID for the interfaces. This determines the order
             in which interfaces are presented to the guest VM";
          type uint16;
          mandatory true;
        }
        leaf type {
          description
            "Interface Type: virtual/passthru";
          type types:iface_type;
          default "virtual";
        }
        leaf model {
          description
            "In case of vitrual: e1000 or virtio. In case of passthrough:
             Model of the NIC. This will be specific to the data center. Data
             centers may have NICs that support virtual functions from
             different vendors, like Intel, Cisco etc. Passthrough is
             not currently supported therefore, not exposing the
             models relavent to PASSTHROUGH as identities";
          type types:iface_model;
          default "virtio";
        }
        leaf network {
          description
            "Network to which this interface needs to be attached.";
          type types:escnetname;
          mandatory true;
        }
        leaf subnet {
          description
            "Subnet within the network to where the port needs to be created.";
          type types:escnetname;
        }
        leaf anycast_address {
          description
            "Anycast address corresponding to this interface";
          type types:escipaddr;
        }
        leaf ip_address {
          description
            "Static IP address for this interface";
          type types:escipaddr;
        }
        leaf mac_address {
          description
            "Static MAC address for this interface";
          type types:escmacaddr;
        }
        container bandwidth {
          leaf min {
            description
              "Minimum bandwidth required for this interface in Mbps";
            type int32;
          }
          leaf max {
            description
              "Maximum bandwidth required for this interface in Mbps";
            type int32;
          }
        }
        container security_groups {
          description
            "Containter for security group(s) set for this instance";
          leaf-list security_group {
            description
              "IP filter rules that determine access control for the VM instance";
            type types:escnetname;
          }
        }
        container allowed_address_pairs {
          description
            "The allowed address is allows one to specify
             arbitrary mac_address/ip_address(cidr) pairs that are
             allowed to pass through a port regardless of subnet.";
          list network {
            key "name";
            description
              "Network allowed on this interface";
            leaf name {
              description
                "Network name or uuid";
              type types:escnetname;
              mandatory true;
            }
          }
          list address {
            key "ip_address";
            description
              "Allowed address on this interface";
            leaf ip_address {
              description
                "Ip address or Subnet address for this network.";
              type types:escipaddr;
              mandatory true;
            }
            leaf netmask {
              description
                "Netmask for the subnet";
              type types:escipaddr;
            }
          }
        }
        uses port_forwarding:esc_port_forwarding;
      }
    }
  }
}
