module esc_property {
  // Generated by yanger -t ncs
  tailf:ncs-device-type "netconf";

  namespace "http://www.cisco.com/esc_property";
  prefix esc_property;

  import tailf-ncs {
    prefix ncs;
  }
  import tailf-common {
    prefix tailf;
  }

  organization "Cisco Systems";
  contact
    "Elie El Ajaltouni <eelajalt@cisco.com>";

  grouping ncs_template_property_list_definition {
    container properties {
      description
        "List of property name/value pairs";
      list property {
        // NCS patched for predictable order
        ordered-by user;
        key "name";
        leaf name {
          description
            "Name/Key of property";
          type string;
        }
        leaf value {
          description
            "Value of property";
          type string;
        }
      }
    }
  }

  grouping ncs_rpc_notif_property_list_definition {
    container properties {
      description
        "List of property name/value pairs";
      list property {
        key "name";
        leaf name {
          description
            "Name/Key of property";
          type string;
        }
        leaf value {
          description
            "Value of property";
          type string;
        }
      }
    }
  }

  grouping live_ncs_property_list_definition {
    container properties {
      description
        "List of property name/value pairs";
      list property {
        key "name";
        leaf name {
          description
            "Name/Key of property";
          type string;
        }
        leaf value {
          description
            "Value of property";
          type string;
        }
      }
    }
  }

  grouping property_list_definition {
    container properties {
      description
        "List of property name/value pairs";
      list property {
        key "name";
        leaf name {
          description
            "Name/Key of property";
          type string;
        }
        leaf value {
          description
            "Value of property";
          type string;
        }
      }
    }
  }
}
