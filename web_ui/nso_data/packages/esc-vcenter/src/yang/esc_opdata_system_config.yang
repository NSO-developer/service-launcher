module esc_opdata_system_config {

  /*
   * This represents operational data of the System configurations for ESC
   */

  namespace "http://www.cisco.com/esc/esc_opdata_system_config";

  prefix "esc_opdata_system_config";

  organization "Cisco Systems";


  revision 2016-02-22 {
    description "Adding container for vmware vim config";
  }
  
  revision 2016-02-01 {
    description "ESC System Configuration details for operational data view";
  }
  
  grouping esc_opdata_system_config {
    description
      "This contains config data of this ESC VM ";
     
    container system_config {

        leaf active_vim {
          description "VIM type";
          type string;
        }

      container openstack_config {

        leaf os_auth_url {
          description "  The Openstack Authentication URL ";
          type string;
        }
        leaf admin_role {
          description " The Admin role setting ";
          type string;
        }
        leaf os_tenant_name {
          description " The Tenant name ";
          type string;
        }
        leaf os_username {
          description " The Openstack username ";
          type string;
        }
        leaf member_role {
          description " The Member role setting ";
          type string;
        }
      }
      
      container vmware_config {

        leaf vcenter_ip {
          description " The vcenter IP address ";
          type string;
        }
        leaf vcenter_port {
          description " The port number for vcenter connection ";
          type string;
        }
        leaf vcenter_username {
          description " The vcenter user name ";
          type string;
        }
      }      
    }
  }
}
