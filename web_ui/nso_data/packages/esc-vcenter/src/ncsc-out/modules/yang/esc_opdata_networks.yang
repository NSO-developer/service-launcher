module esc_opdata_networks {
  // Generated by yanger -t ncs
  tailf:ncs-device-type "netconf";

  namespace "http://www.cisco.com/esc/esc_opdata_networks";
  prefix esc_opdata_networks;

  import ietf-yang-types {
    prefix ietf-yang-types;
  }
  import esc_types {
    prefix types;
  }
  import tailf-ncs {
    prefix ncs;
  }
  import tailf-common {
    prefix tailf;
  }

  organization "Cisco Systems";
  contact
    "Shesha Sreenivasamurthy <shesha@cisco.com>";

  revision 2016-02-04 {
    description
      "add no_gateway to subnet";
  }
  revision 2014-09-06 {
    description
      "Elastic Services Controller Module's tenant's networks' and
                subnetworks' operational data for a tenant";
  }

  grouping ncs_template_esc_opdata_networks {
    description
      "This contains all the operational data of the networks for each tenant";
    container networks {
      list network {
        // NCS patched for predictable order
        ordered-by user;
        description
          "Network and subnet running information";
        key "name";
        leaf name {
          description
            "Network on which the subnet resides";
          type string;
        }
        leaf netid {
          description
            "ID of the network";
          type string;
        }
        leaf shared {
          description
            "Is the network shared among other tenants";
          type string;
        }
        leaf admin_state {
          description
            "Whether the admin state is up or down. True for up
             and false for down. If down, the network does not forward
             packets";
          type string;
        }
        leaf router_external {
          description
            "Indicates whether this network is externally accessible";
          type string;
        }
        leaf provider_physical_network {
          description
            "Specifies the name of the physical network
             over which the virtual network is implemented";
          type string;
        }
        leaf provider_network_type {
          description
            "Specifies the physical mechanism by which
             the Virtual network is implemented";
          type string;
        }
        leaf provider_segmentation_id {
          description
            "ID or tunnel ID of the underlying physical network";
          type string;
        }
        leaf switch_name {
          description
            "(VMWare only) Specifies the name of the switch";
          type string;
        }
        leaf vlan_id {
          description
            "(VMWare only) Specifies the vlan id to assign to this port group";
          type string;
        }
        leaf number_of_ports {
          description
            "(VMWare only) Specifies the number of ports to allocate on the port group";
          type string;
        }
        leaf status {
          description
            "Is the network active or disabled";
          type string;
        }
        container subnets {
          list subnet {
            // NCS patched for predictable order
            ordered-by user;
            description
              "List of subnets associated with the network";
            key "name";
            leaf name {
              description
                "Name of the subnetwork";
              type string;
            }
            leaf subnetid {
              description
                "ID of the subnetwork";
              type string;
            }
            leaf cidr {
              description
                "Classless Inter Domain Routing address";
              type string;
            }
            leaf gateway {
              description
                "Gateway of the subnet";
              type string;
            }
            leaf no_gateway {
              description
                "No gateway for the subnet";
              type string;
            }
            leaf dhcp {
              description
                "Dynamic Host Control Protocol Enabled ?";
              type string;
            }
            leaf ipversion {
              description
                "IP Version 4/6";
              type string;
            }
          }
        }
      }
    }
  }

  grouping ncs_rpc_notif_esc_opdata_networks {
    description
      "This contains all the operational data of the networks for each tenant";
    container networks {
      list network {
        description
          "Network and subnet running information";
        key "name";
        leaf name {
          description
            "Network on which the subnet resides";
          type string;
        }
        leaf netid {
          description
            "ID of the network";
          type ietf-yang-types:uuid;
        }
        leaf shared {
          description
            "Is the network shared among other tenants";
          type boolean;
        }
        leaf admin_state {
          description
            "Whether the admin state is up or down. True for up
             and false for down. If down, the network does not forward
             packets";
          type boolean;
        }
        leaf router_external {
          description
            "Indicates whether this network is externally accessible";
          type boolean;
        }
        leaf provider_physical_network {
          description
            "Specifies the name of the physical network
             over which the virtual network is implemented";
          type string;
        }
        leaf provider_network_type {
          description
            "Specifies the physical mechanism by which
             the Virtual network is implemented";
          type string;
        }
        leaf provider_segmentation_id {
          description
            "ID or tunnel ID of the underlying physical network";
          type uint32;
        }
        leaf switch_name {
          description
            "(VMWare only) Specifies the name of the switch";
          type string;
        }
        leaf vlan_id {
          description
            "(VMWare only) Specifies the vlan id to assign to this port group";
          type uint32;
        }
        leaf number_of_ports {
          description
            "(VMWare only) Specifies the number of ports to allocate on the port group";
          type uint32;
        }
        leaf status {
          description
            "Is the network active or disabled";
          type string;
        }
        container subnets {
          list subnet {
            description
              "List of subnets associated with the network";
            key "name";
            leaf name {
              description
                "Name of the subnetwork";
              type string;
            }
            leaf subnetid {
              description
                "ID of the subnetwork";
              type ietf-yang-types:uuid;
            }
            leaf cidr {
              description
                "Classless Inter Domain Routing address";
              type string;
            }
            leaf gateway {
              description
                "Gateway of the subnet";
              type types:escipaddr;
            }
            leaf no_gateway {
              description
                "No gateway for the subnet";
              type boolean;
            }
            leaf dhcp {
              description
                "Dynamic Host Control Protocol Enabled ?";
              type boolean;
            }
            leaf ipversion {
              description
                "IP Version 4/6";
              type string;
            }
          }
        }
      }
    }
  }

  grouping live_ncs_esc_opdata_networks {
    description
      "This contains all the operational data of the networks for each tenant";
    container networks {
      list network {
        description
          "Network and subnet running information";
        key "name";
        leaf name {
          description
            "Network on which the subnet resides";
          type string;
        }
        leaf netid {
          description
            "ID of the network";
          type ietf-yang-types:uuid;
        }
        leaf shared {
          description
            "Is the network shared among other tenants";
          type boolean;
        }
        leaf admin_state {
          description
            "Whether the admin state is up or down. True for up
             and false for down. If down, the network does not forward
             packets";
          type boolean;
        }
        leaf router_external {
          description
            "Indicates whether this network is externally accessible";
          type boolean;
        }
        leaf provider_physical_network {
          description
            "Specifies the name of the physical network
             over which the virtual network is implemented";
          type string;
        }
        leaf provider_network_type {
          description
            "Specifies the physical mechanism by which
             the Virtual network is implemented";
          type string;
        }
        leaf provider_segmentation_id {
          description
            "ID or tunnel ID of the underlying physical network";
          type uint32;
        }
        leaf switch_name {
          description
            "(VMWare only) Specifies the name of the switch";
          type string;
        }
        leaf vlan_id {
          description
            "(VMWare only) Specifies the vlan id to assign to this port group";
          type uint32;
        }
        leaf number_of_ports {
          description
            "(VMWare only) Specifies the number of ports to allocate on the port group";
          type uint32;
        }
        leaf status {
          description
            "Is the network active or disabled";
          type string;
        }
        container subnets {
          list subnet {
            description
              "List of subnets associated with the network";
            key "name";
            leaf name {
              description
                "Name of the subnetwork";
              type string;
            }
            leaf subnetid {
              description
                "ID of the subnetwork";
              type ietf-yang-types:uuid;
            }
            leaf cidr {
              description
                "Classless Inter Domain Routing address";
              type string;
            }
            leaf gateway {
              description
                "Gateway of the subnet";
              type types:escipaddr;
            }
            leaf no_gateway {
              description
                "No gateway for the subnet";
              type boolean;
            }
            leaf dhcp {
              description
                "Dynamic Host Control Protocol Enabled ?";
              type boolean;
            }
            leaf ipversion {
              description
                "IP Version 4/6";
              type string;
            }
          }
        }
      }
    }
  }

  grouping esc_opdata_networks {
    description
      "This contains all the operational data of the networks for each tenant";
    container networks {
      list network {
        description
          "Network and subnet running information";
        key "name";
        leaf name {
          description
            "Network on which the subnet resides";
          type string;
        }
        leaf netid {
          description
            "ID of the network";
          type ietf-yang-types:uuid;
        }
        leaf shared {
          description
            "Is the network shared among other tenants";
          type boolean;
        }
        leaf admin_state {
          description
            "Whether the admin state is up or down. True for up
             and false for down. If down, the network does not forward
             packets";
          type boolean;
        }
        leaf router_external {
          description
            "Indicates whether this network is externally accessible";
          type boolean;
        }
        leaf provider_physical_network {
          description
            "Specifies the name of the physical network
             over which the virtual network is implemented";
          type string;
        }
        leaf provider_network_type {
          description
            "Specifies the physical mechanism by which
             the Virtual network is implemented";
          type string;
        }
        leaf provider_segmentation_id {
          description
            "ID or tunnel ID of the underlying physical network";
          type uint32;
        }
        leaf switch_name {
          description
            "(VMWare only) Specifies the name of the switch";
          type string;
        }
        leaf vlan_id {
          description
            "(VMWare only) Specifies the vlan id to assign to this port group";
          type uint32;
        }
        leaf number_of_ports {
          description
            "(VMWare only) Specifies the number of ports to allocate on the port group";
          type uint32;
        }
        leaf status {
          description
            "Is the network active or disabled";
          type string;
        }
        container subnets {
          list subnet {
            description
              "List of subnets associated with the network";
            key "name";
            leaf name {
              description
                "Name of the subnetwork";
              type string;
            }
            leaf subnetid {
              description
                "ID of the subnetwork";
              type ietf-yang-types:uuid;
            }
            leaf cidr {
              description
                "Classless Inter Domain Routing address";
              type string;
            }
            leaf gateway {
              description
                "Gateway of the subnet";
              type types:escipaddr;
            }
            leaf no_gateway {
              description
                "No gateway for the subnet";
              type boolean;
            }
            leaf dhcp {
              description
                "Dynamic Host Control Protocol Enabled ?";
              type boolean;
            }
            leaf ipversion {
              description
                "IP Version 4/6";
              type string;
            }
          }
        }
      }
    }
  }
}
