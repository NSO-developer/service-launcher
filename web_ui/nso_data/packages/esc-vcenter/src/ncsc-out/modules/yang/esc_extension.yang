module esc_extension {
  // Generated by yanger -t ncs
  tailf:ncs-device-type "netconf";

  namespace "http://www.cisco.com/esc_extension";
  prefix esc_extension;

  import esc_property {
    prefix property;
  }
  import tailf-ncs {
    prefix ncs;
  }
  import tailf-common {
    prefix tailf;
  }

  organization "Cisco Systems";
  contact
    "Elie El Ajaltouni <eelajalt@cisco.com>";

  revision 2015-08-21 {
    description
      "Add containers within an extension";
  }

  grouping ncs_template_container_list_definition {
    container containers {
      description
        "List of containers";
      list container {
        // NCS patched for predictable order
        ordered-by user;
        key "name";
        leaf name {
          description
            "Name of container";
          type string;
        }
        uses property:ncs_template_property_list_definition;
      }
    }
  }

  grouping ncs_template_extension_list_definition {
    container extensions {
      description
        "List of extensions";
      list extension {
        // NCS patched for predictable order
        ordered-by user;
        key "name";
        leaf name {
          description
            "Name of extension";
          type string;
        }
        uses property:ncs_template_property_list_definition;
        uses ncs_template_container_list_definition;
      }
    }
  }

  grouping ncs_rpc_notif_container_list_definition {
    container containers {
      description
        "List of containers";
      list container {
        key "name";
        leaf name {
          description
            "Name of container";
          type string;
        }
        uses property:ncs_rpc_notif_property_list_definition;
      }
    }
  }

  grouping ncs_rpc_notif_extension_list_definition {
    container extensions {
      description
        "List of extensions";
      list extension {
        key "name";
        leaf name {
          description
            "Name of extension";
          type string;
        }
        uses property:ncs_rpc_notif_property_list_definition;
        uses ncs_rpc_notif_container_list_definition;
      }
    }
  }

  grouping live_ncs_container_list_definition {
    container containers {
      description
        "List of containers";
      list container {
        key "name";
        leaf name {
          description
            "Name of container";
          type string;
        }
        uses property:live_ncs_property_list_definition;
      }
    }
  }

  grouping live_ncs_extension_list_definition {
    container extensions {
      description
        "List of extensions";
      list extension {
        key "name";
        leaf name {
          description
            "Name of extension";
          type string;
        }
        uses property:live_ncs_property_list_definition;
        uses live_ncs_container_list_definition;
      }
    }
  }

  grouping container_list_definition {
    container containers {
      description
        "List of containers";
      list container {
        key "name";
        leaf name {
          description
            "Name of container";
          type string;
        }
        uses property:property_list_definition;
      }
    }
  }

  grouping extension_list_definition {
    container extensions {
      description
        "List of extensions";
      list extension {
        key "name";
        leaf name {
          description
            "Name of extension";
          type string;
        }
        uses property:property_list_definition;
        uses container_list_definition;
      }
    }
  }
}
