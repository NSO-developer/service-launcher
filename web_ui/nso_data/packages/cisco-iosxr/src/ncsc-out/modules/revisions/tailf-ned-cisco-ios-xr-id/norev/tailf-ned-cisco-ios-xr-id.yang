module tailf-ned-cisco-ios-xr-id {
  // Generated by yanger -t ncs
  tailf:ncs-device-type "cli-ned";

  namespace "http://tail-f.com/ned/cisco-ios-xr-id";
  prefix cisco-ios-xr-id;

  import tailf-ncs-ned {
    prefix ned;
  }
  import tailf-ncs {
    prefix ncs;
  }
  import tailf-common {
    prefix tailf;
  }

  identity cisco-ios-xr {
    base ned:cli-ned-id;
  }
}
