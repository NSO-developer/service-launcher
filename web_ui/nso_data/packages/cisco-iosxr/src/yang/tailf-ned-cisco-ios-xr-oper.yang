// =========================================================================
//                          cisco-iosxr NED
// =========================================================================
module tailf-ned-cisco-ios-xr-oper {
  namespace 'http://tail-f.com/ned/cisco-iosxr/oper';
  prefix iosxr-op;

  import tailf-ncs {
    prefix ncs;
  }

  import tailf-common {
    prefix tailf;
  }

  import ietf-inet-types {
    prefix inet;
  }


  // =========================================================================
  // Description
  // =========================================================================
  // This file contains the cdb-oper part of the CISCO XR YANG model.


  /// ========================================================================
  /// cisco-iosxr-oper
  /// ========================================================================

  augment "/ncs:devices/ncs:device/ncs:ned-settings" {
    when "../ncs:device-type/ncs:cli/ncs:ned-id = 'cisco-ios-xr-id:cisco-ios-xr'";

    container cisco-iosxr-oper {
      tailf:info "Cisco XR internal oper data";
      config false;
      tailf:cdb-oper {
        tailf:persistent true;
      }

      // cisco-iosxr-oper / secrets *
      list secrets {
        tailf:cli-suppress-mode;
        tailf:cli-delete-when-empty;
        key "path";
        leaf "path" {
          type string;
        }
        leaf encrypted {
          type string;
        }
        leaf cleartext {
          tailf:hidden all;
          type string;
        }
        leaf regexp {
          tailf:hidden all;
          type string;
        }
      }
    }
  }
}
