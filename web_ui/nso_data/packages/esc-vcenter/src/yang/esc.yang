module esc {
  /*
   * This is the top level YANG module. This imports the datamodel
   * module and that import the rest of YANG modules.
   */
  namespace "http://www.cisco.com/esc/esc";
  prefix "esc";

  import esc_datamodel { prefix "dm"; }
  import tailf-common { prefix "tailf"; }
  import esc_opdata { prefix "op"; }
  import esc_info {prefix "info"; }
  import esc_types { prefix "types"; }
  import esc_network { prefix "network"; }
  import esc_disk { prefix "disk"; }
  import esc_flavor { prefix "flavor"; }
  import esc_vim_connector { prefix "vim"; }

  include "esc_notifications";

  organization "Cisco Systems";

  contact "Shesha Sreenivasamurthy <shesha@cisco.com>";

  description
    "YANG version of the Elastic Service Controller.  This is a complete
     service orchestration module that can dynamically expand and
     reduce your service capacity based on your description of
     LOAD. This module guarantees that the services will be online
     until you tear it down.  This module enables your to: (config it)
     -> (deploy it) -> (forget it)";

  revision 2016-12-02 {
    description "Normalize new LCS policy names";
  }
  revision 2016-11-28 {
    description "Generic LCS_NOTIFY policy action support";
  }
  revision 2016-11-11 {
    description "VM-level software update LCS support";
  }  
  revision 2016-11-08 {
     description 
       "Add new api filterLog to query for logs in escmanager with given parameters.";
  }
  revision 2016-10-18 {
    description "Update placement_group description";
  }
  revision 2016-10-18 {
     description "Remove container default bandwidth values from esc_interface.yang";
  }
  revision 2016-10-06 {
     description "add vim connector and user id in notification";
  }
  revision 2016-10-05 {
    description "Add reboot_time(esc_datamodle.yang)";
  }
  revision 2016-10-04 {
    description "Add more LCS conditions (esc_types.yang)";
  }
  revision 2016-09-23 {
     description "Add top level container esc_system_config containing vim_connectors";
  }
  revision 2016-08-04 {
     description "add extra vm info in notification";
  }
  revision 2016-07-28 {
     description "Added prefix choice for subnet masks";
  }
  revision 2016-07-21 {
     description "Added template_engine field to config data configuration to support no token replacement";
  }
  revision 2016-03-01 {
     description "Added support for recovery VM operations";
  }
  revision 2015-07-23 {
     description "Added support for Tenant Network creation-network directly under tenant";
  }
  revision 2015-07-14 {
    description "Added a new deployment model under tenant";
  }
  revision 2015-06-29 {
    description 
      "ESC Datamodel change to support independent creation of 
       images and flavors";
  }
  revision 2014-06-23 {
    description "Elastic Services Controller Module";
  }

  container esc_datamodel {

    description
      "Top-level container for all ESC database objects.";

    leaf version {
      type types:escversion;
      config false;
      mandatory true;
      description "ESC version";
    }

    /*
     * This contains services and associated definitions of the VMs
     * for the service.  This information is editable only by admin,
     * but readable by all tenants
     */
    uses dm:svc_datamodel;

    /*
     * This is editable by admin and tenants.
     * Tenant-A will not be able to read or write any configs of Tenant-B
     * Configs specified by the tenants are merged with the ones specified
     * by the admin. The values specified by the admin takes presidence.
     */

    container tenants {
      list tenant {
        key "name";
        description "List of tenants";
        leaf name {
          type types:escname;
          mandatory true;
        }
        
        leaf managed_resource {
          type boolean;
          default true;
        }
        
        uses network:esc_network;
        uses dm:tenant_datamodel;
        uses dm:tenant_dep_model;
      }
    }

    /*
     * This represents the external networks that are shared among all
     * the tenants. This is typically created by the admin of the
     * data center typically as part of infrastructure setup.
     * During deployment, the names of the network created here are
     * specified in the interfaces section to associate interfaces
     * wih these networks.
     */
    uses network:esc_network;
    
    /*
     * This contains the images and its attributes. This is created by
     * the admin or the ESC default tenant. 
     */
    uses disk:esc_images;
    
    /*
     * This contains the flavors and its attributes. This is created by 
     * the admin or the ESC default tenant.
     */
    uses flavor:esc_flavors;

    container opdata {
      presence "Indicates that ESC has exported some operational data";
      description
        "This contains all the operational data of the services that have been
         registered and/or instantiated. This is operational data,
         means it is READ-ONLY. Subtrees under this will inherit
         READ-ONLY property, thereby entire subtree becomes READ-ONLY";
      config false;
      tailf:callpoint opdata;
      uses op:esc_opdata;
    } /* END opdata */

    container info {
      presence "Indicates that ESC has exported its infomation";
      description
        "This contains all the information related to versions and copytights";
      config false;
      tailf:callpoint opdata;
      uses info:esc_info;
    } /* END info */
  }

  rpc serviceAction {
    description "Service actions including stop, start, reboot, disable-monitor and enable monitor.";
    tailf:actionpoint escrpc;
    input {
      leaf actionType {
        mandatory true;
        description "Service action type";
        type types:action_types;
      }
      leaf tenantName {
        mandatory true;
        description "Tenant Name";
        type types:escname;
      }
      leaf depName {
        mandatory true;
        description "Deployment Name";
        type types:escname;
      }
      leaf serviceName {
        mandatory true;
        description "Service Name";
        type types:escname;
      }
      leaf serviceVersion {
        mandatory true;
        description "Service Version";
        type types:escname;
      }
    }
  }

  rpc vmAction {
    description "VM actions including stop, start, reboot, disable-monitor and enable monitor.";
    tailf:actionpoint escrpc;
    input {
      leaf actionType {
        mandatory true;
        description "VM action type";
        type types:action_types;
      }
      leaf vmName {
        mandatory true;
        description "VM Name";
        type types:escname;
      }
    }
  }
  
  rpc recoveryVmAction {
    description "Recovery VM actions including do and donot.";
    tailf:actionpoint escrpc;
    input {
      leaf actionType {
        mandatory true;
        description "Recovery VM action type";
        type types:recovery_op_types;
      }
      leaf vmName {
        mandatory true;
        description "VM Name";
        type types:escname;
      }      
    }
  }

  rpc hostAction {
    description "Host actions including enable and disable";
    tailf:actionpoint escrpc;
    input {
      leaf actionType {
        mandatory true;
        description "VM action type";
        type types:host_action_type;
      }
      leaf hostName {
        mandatory true;
        description "Host Name";
        type types:escname;
      }
    }
  }
  


  rpc filterLog {
    description "Query and filter escmanager logs using given parameters";
    tailf:actionpoint escrpc;
    input {
      leaf log_level {
        mandatory false;
        description "One of DEBUG / INFO / WARNING / ERROR / TRACE / FATAL. Results will include all logs at and
                     above the level specified";
        type types:log_level_types;
        default ERROR;
      }
      leaf log_count {
        mandatory false;
        description "Number of logs to return";
        type uint32;
        default 10;
      }
      container classifications {
        leaf-list classification {
          description "Classification values to be used for the log filtering.  For example: 'OS', 'SM'.
                      Logs containing any of the provided classification values will be returned.";
          type types:log_classification_types;     
        }
      }
      container tags {
	list tag {
          key "name";
          leaf name {
            mandatory true;
            description "Tag name to be used for the log filtering.  For example: 'tenant', 'depName'.
                         Logs containing any of the provided tag name plus the tag values will be returned.";
            type types:log_tag_types;
          }
          leaf value {
            mandatory true;
            description "Tag value pairs to be used for the log filtering.  For example: 'adminTenant', 'CSRDeployment'";
            type string;
          }
        }
      }
    }
    output {
      container filterLogResults {
        leaf log_level {
          description "Log level used to filter for the logs.";        
          type types:log_level_types;
        }
        list logs {
          container classifications {
            leaf-list classification {
              description "Classifications used to filter for the logs.";
              type types:log_classification_types;
            }
          }
          container tags {
            list tag {
              key "name";
              leaf name {
                mandatory true;
                description "Tag name used to filter for the logs.";
                type types:log_tag_types;
              }
              leaf value {
                mandatory true;
                description "Tag value used to filter for the logs.";
                type string;
              }
            }
          }
          leaf log_date_time {
            description "Timestamp of the log.";
            type string;
          }
          leaf log_message {
            description "The log message.";
            type string;
          }
        }
      }
    }
  }  

  container esc_system_config {
    description "Top-level container for all ESC system configs.";
    
    /*
     * This contains the virtual infrastructure managers registered
     * with  ESC and information for connecting to them.
     */
    uses vim:esc_vim_connector;
  }
}
