module esc_opdata_default_locators {
  // Generated by yanger -t ncs
  tailf:ncs-device-type "netconf";

  namespace "http://www.cisco.com/esc/esc_opdata_default_locators";
  prefix esc_opdata_default_locators;

  import tailf-ncs {
    prefix ncs;
  }
  import tailf-common {
    prefix tailf;
  }

  organization "Cisco Systems";

  revision 2016-04-01 {
    description
      "ESC configured default VIM locators for operational data view";
  }

  grouping ncs_template_esc_opdata_default_locators {
    description
      "Contains ESC's default VIM-specific resource locator properties for operational data view";
    container default_locators {
      leaf datacenter {
        description
          "The name of the default target datacenter for resources, usually the datacenter ESC resides in.";
        type string;
      }
    }
  }

  grouping ncs_rpc_notif_esc_opdata_default_locators {
    description
      "Contains ESC's default VIM-specific resource locator properties for operational data view";
    container default_locators {
      leaf datacenter {
        description
          "The name of the default target datacenter for resources, usually the datacenter ESC resides in.";
        type string;
      }
    }
  }

  grouping live_ncs_esc_opdata_default_locators {
    description
      "Contains ESC's default VIM-specific resource locator properties for operational data view";
    container default_locators {
      leaf datacenter {
        description
          "The name of the default target datacenter for resources, usually the datacenter ESC resides in.";
        type string;
      }
    }
  }

  grouping esc_opdata_default_locators {
    description
      "Contains ESC's default VIM-specific resource locator properties for operational data view";
    container default_locators {
      leaf datacenter {
        description
          "The name of the default target datacenter for resources, usually the datacenter ESC resides in.";
        type string;
      }
    }
  }
}
