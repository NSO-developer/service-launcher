module esc_datamodel {

  namespace "http://www.cisco.com/esc/esc_datamodel";
  prefix "esc_datamodel";


  /*
   * include all the components of the datamodel
   */
  import esc_policies { prefix "policies"; }
  import esc_network { prefix "network"; }
  import esc_volume { prefix "volume"; }
  import esc_flavor { prefix "flavor"; }
  import esc_disk { prefix "disk"; }
  import esc_interface { prefix "interface"; }
  import esc_kpi { prefix "kpi"; }
  import esc_rules { prefix "rules"; }
  import esc_config_data { prefix "cfg"; }
  import esc_port_forwarding { prefix "pf"; }
  import esc_scaling { prefix "scaling"; }
  import esc_types { prefix "types"; }
  import esc_extension { prefix "extension"; }
  import esc_locators { prefix "locators"; }
  
  organization "Cisco Systems";

  contact "Shesha Sreenivasamurthy <shesha@cisco.com>";
  
  revision 2016-10-04 {
    description "Added reboot_time";
  }
  revision 2016-04-13 {
    description "Added a generic policy container under vm_group";
  }
  revision 2016-03-16 {
    description "Added use of locators";
  }
  revision 2015-11-09 {
    description "Added a leaf to support volume that was precreated in VIM";
  } 
  revision 2015-09-21 {
    description "Added a leaf to config if redeploy is needed after reboot fails upon recovery";
  }
  revision 2015-07-14 {
    description "Added a new deployment model under tenant";
  }
  revision 2015-06-17 {
    description "ESC Datamodel change to add image and flavor that was precreated in vim";
  }
  revision 2015-06-08 {
    description "added esc_port_forwarding";
  }
  revision 2015-06-04 {
    description "updated description";
  }
  revision 2014-06-23 {
    description "ESC Datamodel";
  }

  grouping misc_params {
    container misc {
      description "Some miscelaneous configurations.";
      container watchdog {
        description "Watch Dog";
        leaf hardware {
          description "Watchdog device to be used. i6300esb or ib700";
          type  types:wd_hardware;
        }

        leaf action {
          description "Action when watchdog fires:
                       reset|shutdown|poweroff|pause|debug|none";
          type types:wd_action;
        }
      }
    }
  }

  grouping datamodel {

    uses policies:esc_policies;
    uses network:esc_network;

    list vm_group {
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description "A name for the VM group";
        type types:escname;
        mandatory true;
      }
      leaf image {
        description  "Image refers to pre-existing image in VIM";
        type types:escname;
      }
      leaf flavor {
        description  "Flavor refers to pre-existing flavor in VIM";
        type types:escname;
      }
      leaf volume {
        description  "Volume refers to pre-existing volume in VIM";
        type types:escname;
      }
      leaf software_version {
        description  "Software version of the VM group";
        type types:escname;
      }
      leaf bootup_time {
        description
          "Time in seconds that this VM takes to perform a cold boot. This will
           be the time that ESC waits before deciding that the VM is
           un-bootable.";
        type int32;
        mandatory true;        
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        mandatory true;        
      }
      leaf reboot_time {
      	description
      		"Time in seconds that this VM takes to perform a normal reboot.
      		 if not specified, it will use bootup_time value.";
      	type int32;
      }
      container policies {
        uses policies:esc_policy;
      }
      
      uses misc_params;
      uses volume:esc_volume_deployment;
      uses interface:esc_interface;
      uses kpi:esc_kpi;
      uses rules:esc_rules;
      uses rules:lcm_rules;
      uses cfg:esc_config_data;
      uses pf:esc_port_forwarding;
      uses scaling:esc_scaling;
      uses policies:intra_vm_group_placement;
      uses policies:intra_vm_group_properties;
      uses policies:recovery_policies;
      uses extension:extension_list_definition;
    }
  }

  grouping svc_datamodel {
    container services {
      list service_definition {
        key "name version";
        description "List of services";
        leaf name {
          description "Name of the service";
          type types:escname;
          mandatory true;
        }
        leaf version {
          description "Version of the service";
          type types:escversion;
          mandatory true;
        }
        list vm_group {
          description
          "This section allows one to define properties such as disk, number of
          CPUs, amount of memory";
          key "name";
          min-elements 1;
          leaf name {            
            description "A name for the VM group";
            type types:escname;
            mandatory true;
          }
          uses disk:esc_disk;
          uses flavor:esc_flavor;
        }
      }
    }
  }

  grouping tenant_datamodel {
    container services {
      list service_definition {
        key "deployment_name name version";
        description "List of services requested by the user";
        leaf deployment_name {
          description
            "User specified name. One can have multiple deployments of the
             same service, but have to provide a unique name for each
             deployment";
          type types:escname;
          mandatory true;
        }
        leaf name {
          description "Name of the service";
          type types:escname;
          mandatory true;
        }
        leaf version {
          description "Version of the service";
          type types:escversion;
          mandatory true;
        }
        uses locators:extensible_locators;
        uses datamodel;
      }
    }
  }
  
  grouping tenant_dep_model {
    container deployments {
      list deployment {
        key "name";
        description "List of deployments requested by the user";
        leaf name {
          description
            "User specified name. One can have multiple deployments with a unique name for each
             deployment";
          type types:escname;
          mandatory true;
        }
        
        uses locators:extensible_locators;
        uses datamodel;
        uses rules:lcm_rules;
        
        container deployment_groups {
          leaf-list anti_affinity_group {
              description
                "Reference to the anti-affinity groups to which this deployment pertains to.
                That is, any deployment referencing the same anti-affinity group (in the present or future) 
                will have an anti-affinity relationship to this deployment.";
              type string;
          }
        }
      }
    }
  }
}
