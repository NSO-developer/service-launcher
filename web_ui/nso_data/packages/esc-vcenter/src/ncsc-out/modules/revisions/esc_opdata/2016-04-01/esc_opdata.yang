module esc_opdata {
  // Generated by yanger -t ncs
  tailf:ncs-device-type "netconf";

  namespace "http://www.cisco.com/esc/esc_opdata";
  prefix esc_opdata;

  import esc_opdata_tenant {
    prefix optenant;
  }
  import esc_opdata_devstats {
    prefix opstats;
  }
  import esc_opdata_networks {
    prefix opnetworks;
  }
  import esc_opdata_images {
    prefix opimages;
  }
  import esc_opdata_flavors {
    prefix opflavors;
  }
  import esc_opdata_system_config {
    prefix opsysconf;
  }
  import esc_opdata_default_locators {
    prefix oplocators;
  }
  import tailf-ncs {
    prefix ncs;
  }
  import tailf-common {
    prefix tailf;
  }

  organization "Cisco Systems";
  contact
    "Shesha Sreenivasamurthy <shesha@cisco.com>";

  revision 2016-04-01 {
    description
      "Add ESC Default locators details ";
  }
  revision 2016-02-01 {
    description
      "Add ESC System configuration details ";
  }
  revision 2015-07-06 {
    description
      "Add operational data for images and flavors";
  }
  revision 2014-08-06 {
    description
      "Elastic Services Controller Module's operational data";
  }

  grouping ncs_template_esc_opdata {
    leaf status {
      description
        "Status of ESC";
      type string;
    }
    uses opstats:ncs_template_esc_opdata_devstats;
    uses opsysconf:ncs_template_esc_opdata_system_config;
    uses oplocators:ncs_template_esc_opdata_default_locators;
    uses opnetworks:ncs_template_esc_opdata_networks;
    uses opimages:ncs_template_esc_opdata_images;
    uses opflavors:ncs_template_esc_opdata_flavors;
    uses optenant:ncs_template_esc_opdata_tenant;
  }

  grouping ncs_rpc_notif_esc_opdata {
    leaf status {
      description
        "Status of ESC";
      type string;
    }
    uses opstats:ncs_rpc_notif_esc_opdata_devstats;
    uses opsysconf:ncs_rpc_notif_esc_opdata_system_config;
    uses oplocators:ncs_rpc_notif_esc_opdata_default_locators;
    uses opnetworks:ncs_rpc_notif_esc_opdata_networks;
    uses opimages:ncs_rpc_notif_esc_opdata_images;
    uses opflavors:ncs_rpc_notif_esc_opdata_flavors;
    uses optenant:ncs_rpc_notif_esc_opdata_tenant;
  }

  grouping live_ncs_esc_opdata {
    leaf status {
      description
        "Status of ESC";
      type string;
    }
    uses opstats:live_ncs_esc_opdata_devstats;
    uses opsysconf:live_ncs_esc_opdata_system_config;
    uses oplocators:live_ncs_esc_opdata_default_locators;
    uses opnetworks:live_ncs_esc_opdata_networks;
    uses opimages:live_ncs_esc_opdata_images;
    uses opflavors:live_ncs_esc_opdata_flavors;
    uses optenant:live_ncs_esc_opdata_tenant;
  }

  grouping esc_opdata {
    leaf status {
      description
        "Status of ESC";
      type string;
    }
    uses opstats:esc_opdata_devstats;
    uses opsysconf:esc_opdata_system_config;
    uses oplocators:esc_opdata_default_locators;
    uses opnetworks:esc_opdata_networks;
    uses opimages:esc_opdata_images;
    uses opflavors:esc_opdata_flavors;
    uses optenant:esc_opdata_tenant;
  }
}
