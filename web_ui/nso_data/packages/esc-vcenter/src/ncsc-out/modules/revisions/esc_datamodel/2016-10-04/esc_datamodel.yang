module esc_datamodel {
  // Generated by yanger -t ncs
  tailf:ncs-device-type "netconf";

  namespace "http://www.cisco.com/esc/esc_datamodel";
  prefix esc_datamodel;

  import esc_policies {
    prefix policies;
  }
  import esc_network {
    prefix network;
  }
  import esc_volume {
    prefix volume;
  }
  import esc_flavor {
    prefix flavor;
  }
  import esc_disk {
    prefix disk;
  }
  import esc_interface {
    prefix interface;
  }
  import esc_kpi {
    prefix kpi;
  }
  import esc_rules {
    prefix rules;
  }
  import esc_config_data {
    prefix cfg;
  }
  import esc_port_forwarding {
    prefix pf;
  }
  import esc_scaling {
    prefix scaling;
  }
  import esc_types {
    prefix types;
  }
  import esc_extension {
    prefix extension;
  }
  import esc_locators {
    prefix locators;
  }
  import tailf-ncs {
    prefix ncs;
  }
  import tailf-common {
    prefix tailf;
  }

  organization "Cisco Systems";
  contact
    "Shesha Sreenivasamurthy <shesha@cisco.com>";

  revision 2016-10-04 {
    description
      "Added reboot_time";
  }
  revision 2016-04-13 {
    description
      "Added a generic policy container under vm_group";
  }
  revision 2016-03-16 {
    description
      "Added use of locators";
  }
  revision 2015-11-09 {
    description
      "Added a leaf to support volume that was precreated in VIM";
  }
  revision 2015-09-21 {
    description
      "Added a leaf to config if redeploy is needed after reboot fails upon recovery";
  }
  revision 2015-07-14 {
    description
      "Added a new deployment model under tenant";
  }
  revision 2015-06-17 {
    description
      "ESC Datamodel change to add image and flavor that was precreated in vim";
  }
  revision 2015-06-08 {
    description
      "added esc_port_forwarding";
  }
  revision 2015-06-04 {
    description
      "updated description";
  }
  revision 2014-06-23 {
    description
      "ESC Datamodel";
  }

  grouping ncs_template_misc_params {
    container misc {
      description
        "Some miscelaneous configurations.";
      container watchdog {
        description
          "Watch Dog";
        leaf hardware {
          description
            "Watchdog device to be used. i6300esb or ib700";
          type string;
        }
        leaf action {
          description
            "Action when watchdog fires:
             reset|shutdown|poweroff|pause|debug|none";
          type string;
        }
      }
    }
  }

  grouping ncs_template_datamodel {
    uses policies:ncs_template_esc_policies;
    uses network:ncs_template_esc_network;
    list vm_group {
      // NCS patched for predictable order
      ordered-by user;
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      // NCS drop min-elements statement
      leaf name {
        description
          "A name for the VM group";
        type string;
        // NCS drop mandatory statement
      }
      leaf image {
        description
          "Image refers to pre-existing image in VIM";
        type string;
      }
      leaf flavor {
        description
          "Flavor refers to pre-existing flavor in VIM";
        type string;
      }
      leaf volume {
        description
          "Volume refers to pre-existing volume in VIM";
        type string;
      }
      leaf software_version {
        description
          "Software version of the VM group";
        type string;
      }
      leaf bootup_time {
        description
          "Time in seconds that this VM takes to perform a cold boot. This will
           be the time that ESC waits before deciding that the VM is
           un-bootable.";
        type string;
        // NCS drop mandatory statement
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type string;
        // NCS drop mandatory statement
      }
      leaf reboot_time {
        description
          "Time in seconds that this VM takes to perform a normal reboot.
           if not specified, it will use bootup_time value.";
        type string;
      }
      container policies {
        uses policies:ncs_template_esc_policy;
      }
      uses ncs_template_misc_params;
      uses volume:ncs_template_esc_volume_deployment;
      uses interface:ncs_template_esc_interface;
      uses kpi:ncs_template_esc_kpi;
      uses rules:ncs_template_esc_rules;
      uses rules:ncs_template_lcm_rules;
      uses cfg:ncs_template_esc_config_data;
      uses pf:ncs_template_esc_port_forwarding;
      uses scaling:ncs_template_esc_scaling;
      uses policies:ncs_template_intra_vm_group_placement;
      uses policies:ncs_template_intra_vm_group_properties;
      uses policies:ncs_template_recovery_policies;
      uses extension:ncs_template_extension_list_definition;
    }
  }

  grouping ncs_template_svc_datamodel {
    container services {
      list service_definition {
        // NCS patched for predictable order
        ordered-by user;
        key "name version";
        description
          "List of services";
        leaf name {
          description
            "Name of the service";
          type string;
          // NCS drop mandatory statement
        }
        leaf version {
          description
            "Version of the service";
          type string;
          // NCS drop mandatory statement
        }
        list vm_group {
          // NCS patched for predictable order
          ordered-by user;
          description
            "This section allows one to define properties such as disk, number of
             CPUs, amount of memory";
          key "name";
          // NCS drop min-elements statement
          leaf name {
            description
              "A name for the VM group";
            type string;
            // NCS drop mandatory statement
          }
          uses disk:ncs_template_esc_disk;
          uses flavor:ncs_template_esc_flavor;
        }
      }
    }
  }

  grouping ncs_template_tenant_datamodel {
    container services {
      list service_definition {
        // NCS patched for predictable order
        ordered-by user;
        key "deployment_name name version";
        description
          "List of services requested by the user";
        leaf deployment_name {
          description
            "User specified name. One can have multiple deployments of the
             same service, but have to provide a unique name for each
             deployment";
          type string;
          // NCS drop mandatory statement
        }
        leaf name {
          description
            "Name of the service";
          type string;
          // NCS drop mandatory statement
        }
        leaf version {
          description
            "Version of the service";
          type string;
          // NCS drop mandatory statement
        }
        uses locators:ncs_template_extensible_locators;
        uses ncs_template_datamodel;
      }
    }
  }

  grouping ncs_template_tenant_dep_model {
    container deployments {
      list deployment {
        // NCS patched for predictable order
        ordered-by user;
        key "name";
        description
          "List of deployments requested by the user";
        leaf name {
          description
            "User specified name. One can have multiple deployments with a unique name for each
             deployment";
          type string;
          // NCS drop mandatory statement
        }
        uses locators:ncs_template_extensible_locators;
        uses ncs_template_datamodel;
        uses rules:ncs_template_lcm_rules;
        container deployment_groups {
          leaf-list anti_affinity_group {
            // NCS patched for predictable order
            ordered-by user;
            description
              "Reference to the anti-affinity groups to which this deployment pertains to.
               That is, any deployment referencing the same anti-affinity group (in the present or future)
               will have an anti-affinity relationship to this deployment.";
            type string;
          }
        }
      }
    }
  }

  grouping ncs_rpc_notif_misc_params {
    container misc {
      description
        "Some miscelaneous configurations.";
      container watchdog {
        description
          "Watch Dog";
        leaf hardware {
          description
            "Watchdog device to be used. i6300esb or ib700";
          type types:wd_hardware;
        }
        leaf action {
          description
            "Action when watchdog fires:
             reset|shutdown|poweroff|pause|debug|none";
          type types:wd_action;
        }
      }
    }
  }

  grouping ncs_rpc_notif_datamodel {
    uses policies:ncs_rpc_notif_esc_policies;
    uses network:ncs_rpc_notif_esc_network;
    list vm_group {
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description
          "A name for the VM group";
        type types:escname;
        mandatory true;
      }
      leaf image {
        description
          "Image refers to pre-existing image in VIM";
        type types:escname;
      }
      leaf flavor {
        description
          "Flavor refers to pre-existing flavor in VIM";
        type types:escname;
      }
      leaf volume {
        description
          "Volume refers to pre-existing volume in VIM";
        type types:escname;
      }
      leaf software_version {
        description
          "Software version of the VM group";
        type types:escname;
      }
      leaf bootup_time {
        description
          "Time in seconds that this VM takes to perform a cold boot. This will
           be the time that ESC waits before deciding that the VM is
           un-bootable.";
        type int32;
        mandatory true;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        mandatory true;
      }
      leaf reboot_time {
        description
          "Time in seconds that this VM takes to perform a normal reboot.
           if not specified, it will use bootup_time value.";
        type int32;
      }
      container policies {
        uses policies:ncs_rpc_notif_esc_policy;
      }
      uses ncs_rpc_notif_misc_params;
      uses volume:ncs_rpc_notif_esc_volume_deployment;
      uses interface:ncs_rpc_notif_esc_interface;
      uses kpi:ncs_rpc_notif_esc_kpi;
      uses rules:ncs_rpc_notif_esc_rules;
      uses rules:ncs_rpc_notif_lcm_rules;
      uses cfg:ncs_rpc_notif_esc_config_data;
      uses pf:ncs_rpc_notif_esc_port_forwarding;
      uses scaling:ncs_rpc_notif_esc_scaling;
      uses policies:ncs_rpc_notif_intra_vm_group_placement;
      uses policies:ncs_rpc_notif_intra_vm_group_properties;
      uses policies:ncs_rpc_notif_recovery_policies;
      uses extension:ncs_rpc_notif_extension_list_definition;
    }
  }

  grouping ncs_rpc_notif_svc_datamodel {
    container services {
      list service_definition {
        key "name version";
        description
          "List of services";
        leaf name {
          description
            "Name of the service";
          type types:escname;
          mandatory true;
        }
        leaf version {
          description
            "Version of the service";
          type types:escversion;
          mandatory true;
        }
        list vm_group {
          description
            "This section allows one to define properties such as disk, number of
             CPUs, amount of memory";
          key "name";
          min-elements 1;
          leaf name {
            description
              "A name for the VM group";
            type types:escname;
            mandatory true;
          }
          uses disk:ncs_rpc_notif_esc_disk;
          uses flavor:ncs_rpc_notif_esc_flavor;
        }
      }
    }
  }

  grouping ncs_rpc_notif_tenant_datamodel {
    container services {
      list service_definition {
        key "deployment_name name version";
        description
          "List of services requested by the user";
        leaf deployment_name {
          description
            "User specified name. One can have multiple deployments of the
             same service, but have to provide a unique name for each
             deployment";
          type types:escname;
          mandatory true;
        }
        leaf name {
          description
            "Name of the service";
          type types:escname;
          mandatory true;
        }
        leaf version {
          description
            "Version of the service";
          type types:escversion;
          mandatory true;
        }
        uses locators:ncs_rpc_notif_extensible_locators;
        uses ncs_rpc_notif_datamodel;
      }
    }
  }

  grouping ncs_rpc_notif_tenant_dep_model {
    container deployments {
      list deployment {
        key "name";
        description
          "List of deployments requested by the user";
        leaf name {
          description
            "User specified name. One can have multiple deployments with a unique name for each
             deployment";
          type types:escname;
          mandatory true;
        }
        uses locators:ncs_rpc_notif_extensible_locators;
        uses ncs_rpc_notif_datamodel;
        uses rules:ncs_rpc_notif_lcm_rules;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }

  grouping live_ncs_misc_params {
    container misc {
      description
        "Some miscelaneous configurations.";
      container watchdog {
        description
          "Watch Dog";
        leaf hardware {
          description
            "Watchdog device to be used. i6300esb or ib700";
          type types:wd_hardware;
        }
        leaf action {
          description
            "Action when watchdog fires:
             reset|shutdown|poweroff|pause|debug|none";
          type types:wd_action;
        }
      }
    }
  }

  grouping live_ncs_datamodel {
    uses policies:live_ncs_esc_policies;
    uses network:live_ncs_esc_network;
    list vm_group {
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      // NCS drop min-elements statement
      leaf name {
        description
          "A name for the VM group";
        type types:escname;
        // NCS drop mandatory statement
      }
      leaf image {
        description
          "Image refers to pre-existing image in VIM";
        type types:escname;
      }
      leaf flavor {
        description
          "Flavor refers to pre-existing flavor in VIM";
        type types:escname;
      }
      leaf volume {
        description
          "Volume refers to pre-existing volume in VIM";
        type types:escname;
      }
      leaf software_version {
        description
          "Software version of the VM group";
        type types:escname;
      }
      leaf bootup_time {
        description
          "Time in seconds that this VM takes to perform a cold boot. This will
           be the time that ESC waits before deciding that the VM is
           un-bootable.";
        type int32;
        // NCS drop mandatory statement
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        // NCS drop mandatory statement
      }
      leaf reboot_time {
        description
          "Time in seconds that this VM takes to perform a normal reboot.
           if not specified, it will use bootup_time value.";
        type int32;
      }
      container policies {
        uses policies:live_ncs_esc_policy;
      }
      uses live_ncs_misc_params;
      uses volume:live_ncs_esc_volume_deployment;
      uses interface:live_ncs_esc_interface;
      uses kpi:live_ncs_esc_kpi;
      uses rules:live_ncs_esc_rules;
      uses rules:live_ncs_lcm_rules;
      uses cfg:live_ncs_esc_config_data;
      uses pf:live_ncs_esc_port_forwarding;
      uses scaling:live_ncs_esc_scaling;
      uses policies:live_ncs_intra_vm_group_placement;
      uses policies:live_ncs_intra_vm_group_properties;
      uses policies:live_ncs_recovery_policies;
      uses extension:live_ncs_extension_list_definition;
    }
  }

  grouping live_ncs_svc_datamodel {
    container services {
      list service_definition {
        key "name version";
        description
          "List of services";
        leaf name {
          description
            "Name of the service";
          type types:escname;
          // NCS drop mandatory statement
        }
        leaf version {
          description
            "Version of the service";
          type types:escversion;
          // NCS drop mandatory statement
        }
        list vm_group {
          description
            "This section allows one to define properties such as disk, number of
             CPUs, amount of memory";
          key "name";
          // NCS drop min-elements statement
          leaf name {
            description
              "A name for the VM group";
            type types:escname;
            // NCS drop mandatory statement
          }
          uses disk:live_ncs_esc_disk;
          uses flavor:live_ncs_esc_flavor;
        }
      }
    }
  }

  grouping live_ncs_tenant_datamodel {
    container services {
      list service_definition {
        key "deployment_name name version";
        description
          "List of services requested by the user";
        leaf deployment_name {
          description
            "User specified name. One can have multiple deployments of the
             same service, but have to provide a unique name for each
             deployment";
          type types:escname;
          // NCS drop mandatory statement
        }
        leaf name {
          description
            "Name of the service";
          type types:escname;
          // NCS drop mandatory statement
        }
        leaf version {
          description
            "Version of the service";
          type types:escversion;
          // NCS drop mandatory statement
        }
        uses locators:live_ncs_extensible_locators;
        uses live_ncs_datamodel;
      }
    }
  }

  grouping live_ncs_tenant_dep_model {
    container deployments {
      list deployment {
        key "name";
        description
          "List of deployments requested by the user";
        leaf name {
          description
            "User specified name. One can have multiple deployments with a unique name for each
             deployment";
          type types:escname;
          // NCS drop mandatory statement
        }
        uses locators:live_ncs_extensible_locators;
        uses live_ncs_datamodel;
        uses rules:live_ncs_lcm_rules;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }

  grouping misc_params {
    container misc {
      description
        "Some miscelaneous configurations.";
      container watchdog {
        description
          "Watch Dog";
        leaf hardware {
          description
            "Watchdog device to be used. i6300esb or ib700";
          type types:wd_hardware;
        }
        leaf action {
          description
            "Action when watchdog fires:
             reset|shutdown|poweroff|pause|debug|none";
          type types:wd_action;
        }
      }
    }
  }

  grouping datamodel {
    uses policies:esc_policies;
    uses network:esc_network;
    list vm_group {
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description
          "A name for the VM group";
        type types:escname;
        mandatory true;
      }
      leaf image {
        description
          "Image refers to pre-existing image in VIM";
        type types:escname;
      }
      leaf flavor {
        description
          "Flavor refers to pre-existing flavor in VIM";
        type types:escname;
      }
      leaf volume {
        description
          "Volume refers to pre-existing volume in VIM";
        type types:escname;
      }
      leaf software_version {
        description
          "Software version of the VM group";
        type types:escname;
      }
      leaf bootup_time {
        description
          "Time in seconds that this VM takes to perform a cold boot. This will
           be the time that ESC waits before deciding that the VM is
           un-bootable.";
        type int32;
        mandatory true;
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        mandatory true;
      }
      leaf reboot_time {
        description
          "Time in seconds that this VM takes to perform a normal reboot.
           if not specified, it will use bootup_time value.";
        type int32;
      }
      container policies {
        uses policies:esc_policy;
      }
      uses misc_params;
      uses volume:esc_volume_deployment;
      uses interface:esc_interface;
      uses kpi:esc_kpi;
      uses rules:esc_rules;
      uses rules:lcm_rules;
      uses cfg:esc_config_data;
      uses pf:esc_port_forwarding;
      uses scaling:esc_scaling;
      uses policies:intra_vm_group_placement;
      uses policies:intra_vm_group_properties;
      uses policies:recovery_policies;
      uses extension:extension_list_definition;
    }
  }

  grouping svc_datamodel {
    container services {
      list service_definition {
        key "name version";
        description
          "List of services";
        leaf name {
          description
            "Name of the service";
          type types:escname;
          mandatory true;
        }
        leaf version {
          description
            "Version of the service";
          type types:escversion;
          mandatory true;
        }
        list vm_group {
          description
            "This section allows one to define properties such as disk, number of
             CPUs, amount of memory";
          key "name";
          min-elements 1;
          leaf name {
            description
              "A name for the VM group";
            type types:escname;
            mandatory true;
          }
          uses disk:esc_disk;
          uses flavor:esc_flavor;
        }
      }
    }
  }

  grouping tenant_datamodel {
    container services {
      list service_definition {
        key "deployment_name name version";
        description
          "List of services requested by the user";
        leaf deployment_name {
          description
            "User specified name. One can have multiple deployments of the
             same service, but have to provide a unique name for each
             deployment";
          type types:escname;
          mandatory true;
        }
        leaf name {
          description
            "Name of the service";
          type types:escname;
          mandatory true;
        }
        leaf version {
          description
            "Version of the service";
          type types:escversion;
          mandatory true;
        }
        uses locators:extensible_locators;
        uses datamodel;
      }
    }
  }

  grouping tenant_dep_model {
    container deployments {
      list deployment {
        key "name";
        description
          "List of deployments requested by the user";
        leaf name {
          description
            "User specified name. One can have multiple deployments with a unique name for each
             deployment";
          type types:escname;
          mandatory true;
        }
        uses locators:extensible_locators;
        uses datamodel;
        uses rules:lcm_rules;
        container deployment_groups {
          leaf-list anti_affinity_group {
            description
              "Reference to the anti-affinity groups to which this deployment pertains to.
               That is, any deployment referencing the same anti-affinity group (in the present or future)
               will have an anti-affinity relationship to this deployment.";
            type string;
          }
        }
      }
    }
  }
}
